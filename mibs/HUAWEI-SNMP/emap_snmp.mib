EMAP-MIB DEFINITIONS ::= BEGIN
                                 IMPORTS
huawei
FROM HUAWEI-MIB
                                             OBJECT-GROUP, NOTIFICATION-GROUP
                                                 FROM SNMPv2-CONF
                                             Integer32, Unsigned32, OBJECT-TYPE, MODULE-IDENTITY, NOTIFICATION-TYPE
                                                 FROM SNMPv2-SMI
                                             TEXTUAL-CONVENTION
                                                 FROM SNMPv2-TC;

DisplayString ::= TEXTUAL-CONVENTION
                                             STATUS current
                                             DESCRIPTION 
                                             "Description."
                                             SYNTAX OCTET STRING (SIZE (1..64))
                                             
                                             RowStatus ::= TEXTUAL-CONVENTION
                                             STATUS current
                                             DESCRIPTION 
                                             "Description."
                                             SYNTAX INTEGER
                                             {
                                                     active(1),
                                                     notInService(2),
                                                     notReady(3),
                                                     createAndGo(4),
                                                     createAndWait(5),
                                                     destroy(6)
                                             }
                                             
                                             DateAndTime ::= TEXTUAL-CONVENTION
                                             STATUS current
                                             DESCRIPTION 
                                             "Description."
                                             SYNTAX OCTET STRING (SIZE (8..11))
                                             
                                             RunStatus ::= TEXTUAL-CONVENTION
                                             STATUS current
                                             DESCRIPTION 
                                                     "This integer value represents running status of the system. 
                                                     Depending on situation there may be limits on allowed values.
                                                     Operational values:
                                                     (1) unknown - status has not yet been defined
                                                     (2) normal - there are no activated alarms
                                                     (3) alarm - alarm status
                                             "
                                             SYNTAX INTEGER
                                             {
                                                     unknow(1),
                                                     normal(2),
                                                     alarm(3)
                                             }
                                             
                                             MeasuresRange ::= TEXTUAL-CONVENTION
                                             STATUS current
                                             DESCRIPTION 
                                             "Description."
                                             SYNTAX Integer32
                                             
                                             TruthValue ::= TEXTUAL-CONVENTION
                                             STATUS current
                                             DESCRIPTION 
                                             "Description."
                                             SYNTAX INTEGER
                                             {
                                                     true(1),
                                                     false(2)
                                             }
        huaweiUtility OBJECT IDENTIFIER ::= { huawei 6 }

        hwDev OBJECT IDENTIFIER ::= { huaweiUtility 3 }

        hwSystemPara OBJECT IDENTIFIER ::= { hwDev 1 }

        hwSysIpAddr OBJECT-TYPE
            SYNTAX IpAddress
            MAX-ACCESS read-write
            STATUS current
            DESCRIPTION
                "IP address of the system.
                  It'd better not to modify this address when out-band NMS is used.
                  It will take no effect to separately configure IP address or IP address mask."
            ::= { hwSystemPara 1 }

        hwSysIpMask OBJECT-TYPE
            SYNTAX IpAddress (8..16)
            MAX-ACCESS read-write
            STATUS current
            DESCRIPTION
                "IP address mask of the system.
                  This object can take effect only when hwSysIpAddr is also set.
                "
            ::= { hwSystemPara 2 }

        hwUpgradeVerifyVersion  OBJECT-TYPE
            SYNTAX OCTET STRING (SIZE (0..63))
            MAX-ACCESS read-only
            STATUS current
            DESCRIPTION
                "/"
            ::= { hwSystemPara 31 }

        hwSlotConf OBJECT IDENTIFIER ::= { hwDev 3 }

        hwFrameTable OBJECT-TYPE
            SYNTAX SEQUENCE OF HwFrameEntry
            MAX-ACCESS not-accessible
             STATUS current
             DESCRIPTION
                "The index of this table is hwFrameTable.
                                Shelf description table that describes basic information of a shelf.
                                You can obtain the shelf information, including the shelf type,
                                number of slots, and the shelf running status, and the shelf management status."
            ::= { hwSlotConf 1 }

        hwFrameEntry OBJECT-TYPE
                        SYNTAX HwFrameEntry
            MAX-ACCESS not-accessible
             STATUS current
             DESCRIPTION
                "The index of this table is hwFrameTable.
                                Shelf description table that describes basic information of a shelf.
                                You can obtain the shelf information, including the shelf type,
                                number of slots, and the shelf running status, and the shelf management status."
            INDEX { hwFrameIndex }
            ::= { hwFrameTable 1 }

        HwFrameEntry            ::= SEQUENCE {
                hwFrameIndex
                    Unsigned32,
                hwFrameType
                    Integer32,
                hwFrameAdminStatus
                    INTEGER
            }

        hwFrameIndex OBJECT-TYPE
            SYNTAX Unsigned32
            MAX-ACCESS read-only
            STATUS current
            DESCRIPTION
                "The index of a shelf in the device.
                "
            ::= { hwFrameEntry 1 }

        hwFrameType OBJECT-TYPE
            SYNTAX Integer32
            MAX-ACCESS read-only
            STATUS current
            DESCRIPTION
                "The type of a shelf, which can be obtained from HUAWEI-TC-MIB.mib."
            ::= { hwFrameEntry 2 }

        hwFrameAdminStatus OBJECT-TYPE
            SYNTAX INTEGER
                {
                nooperation(-1),
                                disable(1),
                                enable(2),
                                reset(3),
                                test(4),
                                confirm(5),
                                delete(6),
                                batchconfirm(7),
                                bind(8)
                }
            MAX-ACCESS read-write
            STATUS current
            DESCRIPTION
                "The administration status of frame.
                                Options:
                                1. nooperation(-1) -  default state of the system
                                2. disable(1)      -  indicates that the frame administration state is disable
                                3. enable(2)       -  indicates that the frame administration state is enable
                                4. reset(3)        -  reset the shelf. If you need to reset the shelf immediately,
                                                      perform the operation only. If you need to reset the shelf after a certain period,
                                                      you also need to set hwFrameResetTimeout.
                                                      If you need to reset the control shelf, the entire system is reset;
                                                      otherwise, the control board in the specified shelf is reset
                                5. test(4)         -  test the frame
                                6. confirm(5)      -  confirm the frame
                                7. delete(6)       -  delete the frame info
                                8. batchconfirm(7) -  confirm the boards in a shelf in batches
                                9. bind(8)         -  bind ont serial number with the extended frame ID"
            ::= { hwFrameEntry 6 }

        hwSlotTable OBJECT-TYPE
            SYNTAX SEQUENCE OF HwSlotEntry
            MAX-ACCESS not-accessible
             STATUS current
             DESCRIPTION
                "The board description table, used to manage the running status of
                                boards and board information, such as description of boards,
                                daughter board quantity and board type.
                                The indexes of this table are hwFrameIndex and hwSlotIndex.
                                For the hwFrameIndex object, refer to hwFrameTable.
                                For example, 0.2 indicates that the board is in slot 2, shelf 0."
            ::= { hwSlotConf 2 }

        hwSlotEntry OBJECT-TYPE
                        SYNTAX HwSlotEntry
            MAX-ACCESS not-accessible
             STATUS current
             DESCRIPTION
                "The board description table, used to manage the running status of
                                boards and board information, such as description of boards,
                                daughter board quantity and board type.
                                The indexes of this table are hwFrameIndex and hwSlotIndex.
                                For the hwFrameIndex object, refer to hwFrameTable.
                                For example, 0.2 indicates that the board is in slot 2, shelf 0."
            INDEX { hwSlotType }
            ::= { hwSlotTable 1 }

        HwSlotEntry            ::= SEQUENCE {
                hwSlotType
                    Integer32,
                hwSlotWorkMode
                    INTEGER,
                hwSlotOperStatus 
                    INTEGER
            }

        hwSlotType OBJECT-TYPE
            SYNTAX Integer32
            MAX-ACCESS read-create
            STATUS current
            DESCRIPTION
                "Board type, which is defined in HUAWEI-TC-MIB.mib.
                                The board type supported by a slot varies. For example, a slot can be inserted with a power board only,
                                but certain slots can be inserted with voice service boards and broadband service boards.
                                When adding a board by using the hwSlotRowStatus,
                                you need to specify the board information such as board type and slot number.
                                When adding a board, you need to check whether the board can be inserted in the specified slot."
            ::= { hwSlotEntry 2 }

        hwSlotWorkMode OBJECT-TYPE
            SYNTAX INTEGER
                {
                main(1),
                                standby(2),
                                loadshare(3),
                                nullbackup(4),
                                voice(5),
                                satop(6),
                                pots(7),
                                isdn(8),
                                bonding(9),
                                retransmission(10),
                                nativetdm(11),
                                other(255)
                }
            MAX-ACCESS read-only
            STATUS current
            DESCRIPTION
                "Board working mode that describes whether the board is
                                working in main state or in standby with loadshare, nullbackup, voice, satop state.
                                Options:
                                1. main(1)                 - indicates that the active control board, supporting the get operation only
                                2. standby(2)              - indicates that the standby control board, supporting the get operation only
                                3. loadshare(3)            - indicates that the board working mode is load sharing
                                4. nullbackup(4)           - indicates that the board working mode is backup
                                5. voice(5)                - indicates to get and set the working mode of an EDT service board
                                6. satop(6)                - indicates to get and set the working mode of an EDT service board or TOPB service board
                                7. pots(7)                 - indicates to get and set the working mode of an VDM service board
                                8. isdn(8)                 - indicates to get and set the working mode of an VDM service board
                                9. bonding(9)              - indicates to get and set the working mode of an ADP service board
                                10. retransmission(10)      - indicates to get and set the working mode of an ADP service board
                                11. nativetdm(11)          - indicates to get and set the working mode of a TOPB service board
                                12. other(255)             - indicates other working mode
                                An EDT service board can be running either in voice mode, that is, voice(5), or in broadband mode, that is, satop(6).
                                Setting the working mode of the EDT service board causes board resetting.
                                An VDM service board can be running either in pots mode, that is, pots(7), or in isdn mode, that is, isdn(8).
                                Setting the working mode of the VDM service board causes board resetting.
                                Setting the board working mode may cause board resetting.
                                When you ar"
            ::= { hwSlotEntry 6 }

        hwSlotOperStatus  OBJECT-TYPE
            SYNTAX INTEGER
                {
                null(1),
                                normal(2),
                                fault(3),
                                forbidden(4),
                                autofind(5),
                                config(6),
                                offline(7),
                                abnormal(8),
                                versionerr(9),
                                autoload(10),
                                outofservice(11),
                                graceful(12),
                                shutdown(13),
                                energysavingshutdown(14),
                                hightempshutdown(15),
                                manualshutdown(16),
                                mismatch(17),
                                acoffshutdown(18)
                }
            MAX-ACCESS read-only
            STATUS current
            DESCRIPTION
                "The running status of a board.
                                Options:
                                1. null(1)                  -indicates that the board is null
                                2. normal(2)                -indicates that the board is running normally
                                3. fault(3)                 -indicates that the board is faulty but in position
                                4. forbidden(4)             -indicates that the board is in position but disabled
                                5. autofind(5)              -indicates that the board is in the autofind state. If a board is added through
                                                             hwSlotRowStatus and the board is not confirmed, the board is in the autofind state.
                                                             If a board is inserted in an idle slot, after the report of automatic registration,
                                                             the board is also in the autofind state
                                6. config(6)                -indicates that the board is in the configuration state.
                                                             After a board that is in the auto discovery.
                                                             state is confirmed, data needs to be configured on the board.
                                                             The board is in the configuration state during data configuration.
                                                             After a board is successfully configured, its status is changed from config(6)
                                                             to normal(2). If the configuration fails, the board status is changed from config(6) to fault(3)
                                7. offline(7)               -indicates that the board is faulty and is not in position
                                8. abnormal(8)              -indicates that the board is abnormal
                                9. versionerr(9)            -indicates that the board version is error
                
                                10. autoload(10)            -indicates that the board is in the auto loading state. If detecting a software update,
                                                             the board automa"
            ::= { hwSlotEntry 8 }

        hwUpgrade OBJECT IDENTIFIER ::= { hwDev 22 }

        hwUpgradeRequestID OBJECT-TYPE
            SYNTAX Integer32
            MAX-ACCESS read-write
            STATUS current
            DESCRIPTION
                "/"
            ::= { hwUpgrade 1 }

        hwUpgradeAdmin OBJECT-TYPE
            SYNTAX Integer32
            MAX-ACCESS read-write
            STATUS current
            DESCRIPTION
                "/"
            ::= { hwUpgrade 2 }

        hwUpgradeResetInterval OBJECT-TYPE
            SYNTAX Integer32
            MAX-ACCESS read-write
            STATUS current
            DESCRIPTION
                "/"
            ::= { hwUpgrade 3 }

        hwUpgradeTargetVersion OBJECT-TYPE
            SYNTAX OCTET STRING
            MAX-ACCESS read-write
            STATUS current
            DESCRIPTION
                "/"
            ::= { hwUpgrade 4 }

        hwUpgradeReserveTimeout OBJECT-TYPE
            SYNTAX Integer32
            MAX-ACCESS read-write
            STATUS current
            DESCRIPTION
                "/"
            ::= { hwUpgrade 5 }

        hwUpgradeCapability OBJECT-TYPE
            SYNTAX OCTET STRING
            MAX-ACCESS read-only
            STATUS current
            DESCRIPTION
                "/"
            ::= { hwUpgrade 8 }

        hwLoadBackup OBJECT IDENTIFIER ::= { huaweiUtility 6 }

        hwLoadBackupMon OBJECT IDENTIFIER ::= { hwLoadBackup 1 }

        hwLoadParaTable OBJECT-TYPE
            SYNTAX SEQUENCE OF HwLoadParaEntry
            MAX-ACCESS not-accessible
             STATUS current
             DESCRIPTION
                "Load parameter table, used to load various files to the host
                                through the NMS. The indexes of this table are hwFrameIndex and hwSlotIndex of the board.
                                For example, to load files to the board in slot 3 of frame 0, the index is 0.3."
            ::= { hwLoadBackupMon 1 }

        hwLoadParaEntry OBJECT-TYPE
                        SYNTAX HwLoadParaEntry
            MAX-ACCESS not-accessible
             STATUS current
             DESCRIPTION
                "Load parameter table, used to load various files to the host
                                through the NMS. The indexes of this table are hwFrameIndex and hwSlotIndex of the board.
                                For example, to load files to the board in slot 3 of frame 0, the index is 0.3."
            INDEX { hwLoadServerIpAddr }
            ::= { hwLoadParaTable 1 }

        HwLoadParaEntry            ::= SEQUENCE {
                hwLoadServerIpAddr
                    IpAddress,
                hwLoadMode
                    INTEGER,
                hwLoadFileName
                    OCTET STRING,
                hwLoadContent
                    INTEGER,
                hwLoadBoardType
                    Integer32,
                hwLoadUserName
                    OCTET STRING,
                hwLoadPassword
                    OCTET STRING,
                hwLoadRequestId
                    Integer32,
                hwLoadServerPort
                    Unsigned32
            }

        hwLoadServerIpAddr OBJECT-TYPE
            SYNTAX IpAddress
            MAX-ACCESS read-write
            STATUS current
            DESCRIPTION
                "The IP address of file server."
            ::= { hwLoadParaEntry 1 }

        hwLoadMode OBJECT-TYPE
            SYNTAX INTEGER
                {
                tftp(1),
                modem(2),
                ftp(3),
                smbLoadAnyBoards(4),
                sftp(5),
                other(255)
                }
            MAX-ACCESS read-write
            STATUS current
            DESCRIPTION
                "Load protocol.
                              Options:
                              1.tftp(1)   -indicates that the Trivial File Transfer Protocol (TFTP) is used to perform
                                           the loading through the network port. Select tftp(1) when the transmission mode
                                           of the server is configured to TFTP. When TFTP is used for the loading, you need
                                           not enter the user name (hwLoadUserName) and password (hwLoadPassword).
                              2.modem(2)  -indicates that the XMODEM protocol is used to perform the loading through
                                           the serial port. When you use the HyperTerminal of the OS to perform serial
                                           port configuration on the server, select modem(2). Loading through the serial port
                                           does not require networking and maintenance through the command line interface
                                           does not require NM software.
                              3.ftp(3)    -indicates that the File Transfer Protocol (FTP) is used to perform loading
                                           through the network port. When the transmission mode of the server is configured to FTP,
                                           select ftp(3). When FTP is used for the loading, you need to enter the user name (hwLoadUserName)
                                           and password (hwLoadPassword).
                              4.smbLoadAnyBoards(4)-smbLoadAnyBoards.
                              5.sftp(5)   -indicates that the Secure File Transfer Protocol (SFTP) is used to perform the loading through
                                           the network port. Select sftp(5) when the transmission mode of the server is configured to SFTP.
                                           When SFTP is used for the loading, you need to enter the user name (hwLoadUserName)
                                           and password (hwLoadPassword). The instructions and data are encrypted during transmission.
                              6.other(255)-other.
                              The SFTP transmission mode is recommended."
            ::= { hwLoadParaEntry 2 }

        hwLoadFileName OBJECT-TYPE
            SYNTAX OCTET STRING (SIZE (0..127))
            MAX-ACCESS read-write
            STATUS current
            DESCRIPTION
                "The name of the file to be loaded."
            ::= { hwLoadParaEntry 3 }

        hwLoadContent OBJECT-TYPE
            SYNTAX INTEGER
                {
                program(1),
                database(2),
                patch(3)
                }
            MAX-ACCESS read-write
            STATUS current
            DESCRIPTION
                "Type of the loaded file.
                                Options:
                                1.noloadcontent(-1)               -no file.
                                2.program(1)                      -program file.
                                3.database(2)                     -database file.
                                4.patch(3)                        -patch file.
                                5.shellMacro(4)                   -shell macro file.
                                6.resLocal(5)                     -local resource file.
                                7.resGeneral(6)                   -general resource file.
                                8.cpeDrive(7)                     -cpe drive.
                                9.programDatabase(8)              -database file.
                                10.programBios(9)                 -bios file.
                                11.programApp(10)                 -application program.
                                12.logicFpga(11)                  -fpga logic file.
                                13.logicCpld(12)                  -Cpld logic file.
                                14.logicPci(13)                   -pci logic file.
                                15.logicAfc(14)                   -afc logic file.
                                16.programMicroCode(15)           -micro code file.
                                17.programFirmware(16)            -application program of pinch board.
                                18.programHelp(17)                -program help file.
                                19.programDataFlow(18)            -flow file of card management point.
                                20.programBootFile(19)            -Boot program file of board.
                                21.logciPa(20)                    -Boot program file of board start.
                                22.webExp(21)                     -web exp file.
                                23.webNev(22)                     -web nev file.
                                24.webHelp(23)                    -web help file.
                                25.programBsp(24)                 -bsp program file.
                                26.verBinFile(25)                 -packet file.
                                27.configurationFile(26)          -configuration file.
                                28.configurationIni(40)           -configuration file of ini formatini.
                   "
            ::= { hwLoadParaEntry 4 }

        hwLoadBoardType OBJECT-TYPE
            SYNTAX Integer32
            MAX-ACCESS read-write
            STATUS current
            DESCRIPTION
                "The type of the board to be loaded, which is defined in HUAWEI-TC-MIB.mib."
            ::= { hwLoadParaEntry 5 }

        hwLoadUserName OBJECT-TYPE
            SYNTAX OCTET STRING (SIZE (0..31))
            MAX-ACCESS read-write
            STATUS current
            DESCRIPTION
                "The name of load user, which is required in FTP mode and SFTP mode
                                but is not required in any other modes."
            ::= { hwLoadParaEntry 8 }

        hwLoadPassword OBJECT-TYPE
            SYNTAX OCTET STRING (SIZE (0..16))
            MAX-ACCESS read-write
            STATUS current
            DESCRIPTION
                "The load user password, which is required in FTP mode and SFTP mode
                                but is not required in any other modes."
            ::= { hwLoadParaEntry 9 }

        hwLoadRequestId OBJECT-TYPE
            SYNTAX Integer32
            MAX-ACCESS read-write
            STATUS current
            DESCRIPTION
                "The loading request ID, which identifies the loading request delivered by the NMS.
                                According to the ID, you can query hwOperationInfoTable to obtain the status and
                                results of each loading operation.
                                A request ID can be any integer in the range of 0-0xFFFFFFFF,
                                but the IDs of different loading requests are not duplicate.
                                This object cannot be set independently.
                                The hwLoadRequestId value of -1 indicates there is no loading operation."
            ::= { hwLoadParaEntry 12 }

        hwLoadServerPort OBJECT-TYPE
            SYNTAX Unsigned32 (0..65535)
            MAX-ACCESS read-write
            STATUS current
            DESCRIPTION
                "Monitoring port on the SFTP server.
                                Range: 0-65535
                                Default: 22
                                The invalid value is 65535."
            ::= { hwLoadParaEntry 13 }

        hwBackupParaTable OBJECT-TYPE
            SYNTAX SEQUENCE OF HwBackupParaEntry
            MAX-ACCESS not-accessible
             STATUS current
             DESCRIPTION
                "Backup parameter table, used to back up various files of the host through the NMS.
                  This table is used to back up important system data. Therefore, configure a high
                  access permission for this table.
                  The indexes of this table are hwFrameIndex and hwSlotIndex of the board.
                  For example, to back up the files of the board in slot 3 of frame 0, the index is 0.3.
                  
                "
            ::= { hwLoadBackupMon 2 }

        hwBackupParaEntry OBJECT-TYPE
                        SYNTAX HwBackupParaEntry
            MAX-ACCESS not-accessible
             STATUS current
             DESCRIPTION
                "Backup parameter table, used to back up various files of the host through the NMS.
                  This table is used to back up important system data. Therefore, configure a high
                  access permission for this table.
                  The indexes of this table are hwFrameIndex and hwSlotIndex of the board.
                  For example, to back up the files of the board in slot 3 of frame 0, the index is 0.3.
                  
                "
            INDEX { hwBackupServerIpAddr }
            ::= { hwBackupParaTable 1 }

        HwBackupParaEntry            ::= SEQUENCE {
                hwBackupServerIpAddr
                    IpAddress,
                hwBackupMode
                    INTEGER,
                hwBackupFileName
                    OCTET STRING,
                hwBackupContent
                    INTEGER,
                hwBackupUserName
                    OCTET STRING,
                hwBackupPassword
                    OCTET STRING,
                hwBackupRequestID
                    Integer32,
                hwBackupServerPort
                    Unsigned32
            }

        hwBackupServerIpAddr OBJECT-TYPE
            SYNTAX IpAddress
            MAX-ACCESS read-write
            STATUS current
            DESCRIPTION
                "The IP address of file server."
            ::= { hwBackupParaEntry 1 }

        hwBackupMode OBJECT-TYPE
            SYNTAX INTEGER
                {
                tftp(1),
                modem(2),
                ftp(3),
                sftp(5),
                other(6)
                }
            MAX-ACCESS read-write
            STATUS current
            DESCRIPTION
                "Load protocol.
                  Options:
                  1.tftp(1)  -indicates that the backup is performed by using TFTP through the
                              network port. Select tftp(1) when the transmission mode of the server is
                              configured to TFTP.When TFTP is used in the backup, you need not enter the
                              user name and password.
                  2.modem(2) -indicates that the backup is performed by using the Xmodem serial
                              port protocol through the serial port. When you use the HyperTerminal of
                              the OS to configure the serial port on the server, select modem(2).
                              Loading through the serial port does not require networking and maintenance
                              through the command line interface does not require NM software.
                  3.ftp(3)   -indicates that the backup is performed by using FTP through the network
                              port. Select ftp when the transmission mode of the server is configured to FTP.
                              When FTP is used for file backup, you need to enter the user name and password.
                  4.sftp(5)  -indicates that the backup is performed by using SFTP through the network port.
                              Select sftp(5) when the transmission mode of the server is configured to SFTP.
                              When SFTP is used for file backup, the instructions and data are encrypted
                              during transmission.
                  5.other(6) -other.
                  The SFTP transmission mode is recommended."
            ::= { hwBackupParaEntry 2 }

        hwBackupFileName OBJECT-TYPE
            SYNTAX OCTET STRING (SIZE (0..128))
            MAX-ACCESS read-write
            STATUS current
            DESCRIPTION
                "The name of backup file."
            ::= { hwBackupParaEntry 3 }

        hwBackupContent OBJECT-TYPE
            SYNTAX INTEGER
                {
                nobackupcontent(-1),
                database(1),
                shellMacro(2),
                log(3),
                bill(4),
                alarm(5),
                configurationFile(14),
                program(15),
                reslocal(16),
                resgeneral(17),
                patch(18),
                programDatabase(19),
                programBios(20),
                programApp(21),
                logicFpga(22),
                logicCpld(23),
                logicPci(24),
                logicAfc(25),
                programMicroCode(26),
                programFireware(27),
                programDataFlow(28),
                programBootFile(29),
                logciPa(30),
                webExp(31),
                webNev(32),
                webHelp(33),
                programBsp(34),
                configurationIni(40),
                configurationEfs(41),
                configurationCli(42),
                programCurrent(45),
                programOther(46),
                bcdcInfo(47),
                license(49),
                programExtendedBios(51),
                boardinfo(60),
                extendedBootRom(61),
                defaultCfg(62),
                exception(63),
                versionDescribe(64),
                emuelabel(65),
                emuproofelabel(66),
                backboardelabel(67),
                nmscollectinfo(68),
                trapsyninfo(69),
                digitmap(70),
                h248Profile(71),
                sipProfile(72),
                elabel(73),
                sipDigitmap(74),
                iop(75),
                port(76),
                script(77),
                voice(78),
                framePnp(79),
                boardPnp(80),
                subboardPnp(81),
                resetRecord(82),
                hwStatusCollectInfo(83),
                deviceCapXml(84),
                cabinetelabel(120),
                batteryelabel(121),
                deviceCapabilityFile(122),
                powerRunData(123),
                crosstalkCouplingMatrix(131),
                vdsl2Xlin(132),
                ibmsFile(133),
                userfile(134),
                vectoring(135),
                xdslPortResetInfo(136),
                frameelabel(137),
                rootfs(138),
                uimage(139),
                initrd(140),
                atiboardelabel(141),
                boardspectrum(150)
                
                }
            MAX-ACCESS read-write
            STATUS current
            DESCRIPTION
                "Type of the backup file.
                  Options:
                  1.nobackupcontent(-1)             -no file.
                  2.database(1)                     -database file.
                  3.shellMacro(2)                   -shell macro file.
                  4.log(3)                          -log file.
                  5.bill(4)                         -bill file.
                  6.alarm(5)                        -alarm file.
                  7.configurationFile(14)           -configuration file.
                  8.program(15)                     -program file.
                  9.reslocal(16)                    -local resource file.
                  10.resgeneral(17)                 -general resource file.
                  11.patch(18)                      -patch file.
                  12.programDatabase(19)            -database file.
                  13.programBios(20)                -bios file.
                  14.programApp(21)                 -application file.
                  15.logicFpga(22)                  -fpga logic file.
                  16.logicCpld(23)                  -Cpld logic file.
                  17.logicPci(24)                   -pci logic file.
                  18.logicAfc(25)                   -afc logic file.
                  19.programMicroCode(26)           -micro-code file.
                  20.programFireware(27)            -application program of pinch board.
                  21.programDataFlow(28)            -flow file of card management point.
                  22.programBootFile(29)            -boot program file of the board start.
                  23.logciPa(30)                    -fpga logic file of the pinch board.
                  24.webExp(31)                     -web exp file.
                  25.webNev(32)                     -web nev file.
                  26.webHelp(33)                    -web help file.
                  27.programBsp(34)                 -bsp program file.
                  28.configurationIni(40)           -not supported.
                  29.configurationEfs(41)           -not supported.
                  30.configurationCli(42)           -not supported.
                  31.programCurrent(45)             -not supported.
                  32.programOther(46)               -not supported.
                  33.bcdcInfo(47)                   -bcdc description system in ini file.
                  34.license(49)                    -license file.
                  35.programExtendedBios(51)        -extended bios file.
                  36.boardinfo(60)                 "
            ::= { hwBackupParaEntry 4 }

        hwBackupUserName OBJECT-TYPE
            SYNTAX OCTET STRING (SIZE (0..40))
            MAX-ACCESS read-write
            STATUS current
            DESCRIPTION
                "The backup user name, which is required in FTP mode and SFTP mode
                  but is not required in TFTP mode.
                 "
            ::= { hwBackupParaEntry 6 }

        hwBackupPassword OBJECT-TYPE
            SYNTAX OCTET STRING (SIZE (0..40))
            MAX-ACCESS read-write
            STATUS current
            DESCRIPTION
                "The backup user password, which is required in FTP mode and SFTP mode
                  but is not required in TFTP mode."
            ::= { hwBackupParaEntry 7 }

        hwBackupRequestID OBJECT-TYPE
            SYNTAX Integer32
            MAX-ACCESS read-write
            STATUS current
            DESCRIPTION
                "The backup request ID, which identifies a backup request delivered by the NMS.
                  According to the ID, you can query hwOperationInfoTable to obtain
                  the status and results of each backup operation.
                  An backup request ID can be any integer in the range of 0-0xFFFFFFFF.
                  But, the IDs of different backup requests cannot duplicate.
                  This object cannot be set independently.
                  The hwBackupRequestID value of -1 indicates there is no backup operation."
            ::= { hwBackupParaEntry 9 }

        hwBackupServerPort OBJECT-TYPE
            SYNTAX Unsigned32 (0..65535)
            MAX-ACCESS read-write
            STATUS current
            DESCRIPTION
                "SFTP server listen port.
                  Range: 0-65535
                  Default: 22
                  The invalid value is 65535."
            ::= { hwBackupParaEntry 10 }

        hwOperationInfo OBJECT IDENTIFIER ::= { hwLoadBackup 4 }

        hwOperationInfoTable OBJECT-TYPE
            SYNTAX SEQUENCE OF HwOperationInfoEntry
            MAX-ACCESS not-accessible
             STATUS current
             DESCRIPTION
                "Operation information table. Through this table,
                                you can query the status and results of data saving, loading,
                                backup, upgrading without service interruption, patch rollback,
                                and cloning operations on the NMS. The index of this table is hwOperationReqID.
                                hwOperationReqID is an operation request ID."
            ::= { hwOperationInfo 1 }

        hwOperationInfoEntry OBJECT-TYPE
                        SYNTAX HwOperationInfoEntry
            MAX-ACCESS not-accessible
             STATUS current
             DESCRIPTION
                "Operation information table. Through this table,
                                you can query the status and results of data saving, loading,
                                backup, upgrading without service interruption, patch rollback,
                                and cloning operations on the NMS. The index of this table is hwOperationReqID.
                                hwOperationReqID is an operation request ID."
            INDEX { hwOperationReqID }
            ::= { hwOperationInfoTable 1 }

        HwOperationInfoEntry            ::= SEQUENCE {
                hwOperationReqID
                    Integer32,
                hwOperationReqStatus
                    INTEGER,
                hwOperationProgress
                    Integer32,
                hwOperationReqErrStatus
                    Integer32
            }

        hwOperationReqID OBJECT-TYPE
            SYNTAX Integer32
            MAX-ACCESS read-only
            STATUS current
            DESCRIPTION
                "The requestID of this operation. This object together with hwOperationReqType,
                                identifies different operations of different types."
            ::= { hwOperationInfoEntry 1 }

        hwOperationReqStatus OBJECT-TYPE
            SYNTAX INTEGER
                {
                initial(1),
                datascanning(2),
                transferring(3),
                saving(4),
                success(5),
                fail(6),
                ioupgrade(11)
                
                }
            MAX-ACCESS read-only
            STATUS current
            DESCRIPTION
                "Current status of an operation request.
                                Options:
                                1.initial(1)     -indicates that the operation is in the preparation phase.
                                2.datascanning(2)-indicates that the operation is in the data collection phase.
                                3.transferring(3)-indicates that the operation is in the data transmission phase.
                                4.saving(4)      -indicates that the operation is in the data saving phase.
                                5.success(5)     -indicates that the operation is successful.
                                6.fail(6)        -indicates that the operation fails.
                                7.uninterruptedAutoUpgradeResetStandby(7)
                                 -indicates that automatic upgrade without service interruption is in the following state:
                                  the standby control board is being started after reset.
                                8.uninterruptedAutoUpgradeBatchHotBackupFirst(8)
                                 -indicates that automatic upgrade without service interruption is in the following state:
                                  the standby control board is restarted and hot backup on the host is under way.
                                9.uninterruptedAutoUpgradeSwitchOver(9)
                                 -indicates that automatic upgrade without service interruption is in the following state:
                                  the active control board switches to the standby one and is being restarted.
                               10.uninterruptedAutoUpgradeBatchHotBackupSecond(10)
                                 -indicates that automatic upgrade without service interruption is in the following state:
                                  the current standby control board is already restarted and hot backup on the host is being performed.
                               11.ioupgrade(11)   -indicates that automatic upgrade is in the following state:
                                  the upgrade of the service board.
                               12.systemreboot(12)-indicates that automatic upgrade with service interruption is in the following state:
                                  the system is rebooting.
                               13.serviceboardloading(13)--indicates that aut"
            ::= { hwOperationInfoEntry 3 }

        hwOperationProgress OBJECT-TYPE
            SYNTAX Integer32 (0..100)
            MAX-ACCESS read-only
            STATUS current
            DESCRIPTION
                "The progress of the operation.
                                Range: 0-100."
            ::= { hwOperationInfoEntry 4 }

        hwOperationReqErrStatus OBJECT-TYPE
            SYNTAX Integer32
            MAX-ACCESS read-only
            STATUS current
            DESCRIPTION
                "The error code of this operation. The returned error code is an NMS error code.
                                The value 0 means 'No error';
                                The value 6561510 means 'Failed to transfer the file';
                                The value 6561553 means 'Username or password error';
                                The value 6561620 means 'The server is unreachable';
                                The value 6561623 means 'Failed to operate the remote file';
                                The value 6561625 means 'The SSH key is incorrect';
                                The value 6561626 means 'The path does not exist';
                                The value 6561627 means 'The file does not exist'."
            ::= { hwOperationInfoEntry 5 }

        hwSiteMonitorMIB OBJECT IDENTIFIER ::= { huaweiUtility 164 }

        hwSiteMonitorMIBObjects OBJECT IDENTIFIER ::= { hwSiteMonitorMIB 1 }

        hwSiteInfo OBJECT IDENTIFIER ::= { hwSiteMonitorMIBObjects 1 }

        hwSiteSummary OBJECT IDENTIFIER ::= { hwSiteInfo 1 }

        hwSiteId OBJECT-TYPE
            SYNTAX OCTET STRING (SIZE (0..8))
            MAX-ACCESS read-only
            STATUS current
            DESCRIPTION
                "Site ID, default value: 000,000.Naming rule of the site device ID (six digits): 
                The first three digits indicate the device name and the last three digits indicate the serial number (SN) of the device. 
                If the last three digits are 000, it indicates a virtual device."
            ::= { hwSiteSummary 1 }

        hwSiteName OBJECT-TYPE
            SYNTAX OCTET STRING (SIZE (0..63))
            MAX-ACCESS read-write
            STATUS current
            DESCRIPTION
                "Site name, which users can configure, is used to specify a site.  Otherwise, the configured character can not be any other languages except English."
            ::= { hwSiteSummary 2 }

        hwSiteAdminAddr OBJECT-TYPE
            SYNTAX Unsigned32 (0..65535)
            MAX-ACCESS read-write
            STATUS current
            DESCRIPTION
                "Site administrant address, which users can assigned, is the unique ID of a site. 
                It is used for device management by NMS, and value range is 0 to 65535. "
            ::= { hwSiteSummary 3 }

        hwSiteDescription OBJECT-TYPE
            SYNTAX OCTET STRING (SIZE (0..63))
            MAX-ACCESS read-write
            STATUS current
            DESCRIPTION
                "Site description. It is of the character string type. It is used to describe the site information such as the site location, which users can configure.  
                Otherwise, the configured character can not be any other languages except English."
            ::= { hwSiteSummary 4 }

        hwNetIdentifier OBJECT-TYPE
            SYNTAX OCTET STRING (SIZE (0..63))
            MAX-ACCESS read-write
            STATUS current
            DESCRIPTION
                "NE ID. It is of the character string type. It is the unique ID of the site (an independent network element (NE)) on the network. 
                Otherwise, the configured character can not be any other languages except English."
            ::= { hwSiteSummary 5 }

        hwSiteIp OBJECT-TYPE
            SYNTAX OCTET STRING (SIZE (8..16))
            MAX-ACCESS read-only
            STATUS current
            DESCRIPTION
                "Site IP address, default value is 192.168.0.10. Users need to configure the site IP address."
            ::= { hwSiteSummary 6 }

        hwSiteNetmask OBJECT-TYPE
            SYNTAX OCTET STRING (SIZE (8..16))
            MAX-ACCESS read-only
            STATUS current
            DESCRIPTION
                "Site netmask, default value is 255.255.255.0. Users need to configure the site netmask."
            ::= { hwSiteSummary 7 }

        hwSiteGateway OBJECT-TYPE
            SYNTAX OCTET STRING (SIZE (8..16))
            MAX-ACCESS read-only
            STATUS current
            DESCRIPTION
                "Site gateway, default value: 192.168.0.1. Users need to configure the site gateway."
            ::= { hwSiteSummary 8 }

        hwSiteRunningStatus OBJECT-TYPE
            SYNTAX INTEGER
                {
                normal(1),
                alarm(2)
                }
            MAX-ACCESS read-only
            STATUS current
            DESCRIPTION
                "State of the site alarm state. It is an enumeration type: 
                  If the enumeration value is 1, it indicates that the site is in the normal state;
                  If the enumeration value is 2, it indicates that the site is in the alarm state."
            ::= { hwSiteSummary 10 }

        hwSiteAlarms OBJECT IDENTIFIER ::= { hwSiteInfo 2 }

        hwDeviceTrapOrdinalNumber OBJECT-TYPE
            SYNTAX Unsigned32 ( 0..4294967295)
            MAX-ACCESS read-write
            STATUS current
            DESCRIPTION
                "Site device event trap serial number (SN) is the unique ID of the device event trap. It is used to resend and synchronize event traps.
                Its value range is 0 to 4294967295. When the value exceeds the maximum value, the system automatically clears the value and numbers the alarm from 0 to 4294967295.   
                If the network management system (NMS) recieve the alarm number is not consequential, in such case that it notifies the SNMP agent the event trap number required.  
                So the monitor send the 100 event trap messages in maximum, after consequencial number required by NMS again. Specially, if NMS set the value to 0, the agent would clear the alarm queue automatically."
            ::= { hwSiteAlarms 1 }

        hwAlarmTrapOrdinalNumber OBJECT-TYPE
            SYNTAX Unsigned32 ( 0..4294967295)
            MAX-ACCESS read-write
            STATUS current
            DESCRIPTION
                "Site alarm serial number (SN) is the unique ID of the alarm Trap. It is used to resend and synchronize alarms. Its value range is 0 to 4294967295. When the value exceeds the maximum value, the system automatically clears the value and numbers the alarm from 0 to 4294967295.  
                If the network management system (NMS) recieve the alarm number is not consequential, in such case that it notifies the SNMP agent the alarm number required.  So the monitor send the 100 alarm messages in maximum, after consequencial number required by NMS again. Specially, if NMS set the value to 0, the agent would clear the alarm queue automatically."
            ::= { hwSiteAlarms 2 }

        hwAlarmQuantity OBJECT-TYPE
            SYNTAX Unsigned32 (0..65535)
            MAX-ACCESS read-only
            STATUS current
            DESCRIPTION
                "Alarm number in site alarm list which are support. 
                It is used for alarm list management by NMS, and value range is 0 to 65535. "
            ::= { hwSiteAlarms 3 }

        hwSiteActiveAlarmTable OBJECT-TYPE
            SYNTAX SEQUENCE OF HwSiteActiveAlarmEntry
            MAX-ACCESS not-accessible
             STATUS current
             DESCRIPTION
                ""
            ::= { hwSiteAlarms 99 }

        hwSiteActiveAlarmEntry OBJECT-TYPE
                        SYNTAX HwSiteActiveAlarmEntry
            MAX-ACCESS not-accessible
             STATUS current
             DESCRIPTION
                ""
            INDEX { hwActiveAlarmIndex }
            ::= { hwSiteActiveAlarmTable 1 }

        HwSiteActiveAlarmEntry            ::= SEQUENCE {
                hwActiveAlarmIndex
                    Integer32,
                hwActiveAlarmText
                    OCTET STRING,
                hwActiveAlarmLevel
                    INTEGER,
                hwActiveAlarmSigDesc
                    OCTET STRING,
                hwActiveAlarmTime
                    OCTET STRING,
                hwActiveAlarmRowStatus
                    RowStatus,
                hwSMUSiteName
                    OCTET STRING,
                hwSMUSiteAdminAddr
                    Unsigned32,
                hwSMUNetIdentifier
                    OCTET STRING,
                hwSMUSiteDescription
                    OCTET STRING,
                hwEquipId
                    Unsigned32,
                hwEquipName
                    OCTET STRING
            }

        hwActiveAlarmIndex OBJECT-TYPE
            SYNTAX Integer32 (1..65535)
            MAX-ACCESS read-only
            STATUS current
            DESCRIPTION
                "Site active alarm table index. It is the unique ID of the site alarm."
            ::= { hwSiteActiveAlarmEntry 1 }

        hwActiveAlarmText OBJECT-TYPE
            SYNTAX OCTET STRING (SIZE (0..63))
            MAX-ACCESS read-only
            STATUS current
            DESCRIPTION
                "Active alarm name. It is of the character string type, and used to specify the content of a specific alarm.  "
            ::= { hwSiteActiveAlarmEntry 2 }

        hwActiveAlarmLevel OBJECT-TYPE
            SYNTAX INTEGER
                {
                critical(1),
                major(2),
                minor(3),
                warning(4),
                unknown(255)
                }
            MAX-ACCESS read-only
            STATUS current
            DESCRIPTION
                "Active alarm level, which users can configure the alarm severity, is an enumeration type:
                    If the enumeration value is 1, it indicates a critical alarm;
                    If the enumeration value is 2, it indicates a major alarm;
                    If the enumeration value is 3, it indicates a minor alarm;
                    If the enumeration value is 4, it indicates a warning;
                    If the enumeration value is 255, it indicates a unknown;"
            ::= { hwSiteActiveAlarmEntry 3 }

        hwActiveAlarmSigDesc OBJECT-TYPE
            SYNTAX OCTET STRING (SIZE (0..127))
            MAX-ACCESS read-only
            STATUS current
            DESCRIPTION
                "Active alarm signal description. It is used to add and describe alarm content. Users can define the description of the alarm.
                  Otherwise, the configured character can not be any other languages except English."
            ::= { hwSiteActiveAlarmEntry 4 }

        hwActiveAlarmTime OBJECT-TYPE
            SYNTAX OCTET STRING (SIZE (0..127))
            MAX-ACCESS read-only
            STATUS current
            DESCRIPTION
                "Active alarm time. It is of the character string type, and used to specify the content of a specific alarm.  "
            ::= { hwSiteActiveAlarmEntry 5 }

        hwActiveAlarmRowStatus OBJECT-TYPE
            SYNTAX RowStatus
            MAX-ACCESS read-create
            STATUS current
            DESCRIPTION
                "Rowstatus of active alarm table."
            ::= { hwSiteActiveAlarmEntry 100 }

        hwSMUSiteName OBJECT-TYPE
            SYNTAX OCTET STRING (SIZE (0..63))
            MAX-ACCESS read-only
            STATUS current
            DESCRIPTION
                "Site name, which users can configure, is used to specify a site.  Otherwise, the configured character can not be any other languages except English."
            ::= { hwSiteActiveAlarmEntry 6 }

        hwSMUSiteAdminAddr OBJECT-TYPE
            SYNTAX Unsigned32 (0..65535)
            MAX-ACCESS read-only
            STATUS current
            DESCRIPTION
                "Site administrant address, which users can assigned, is the unique ID of a site. It is used for device management by NMS, and value range is 0 to 65535. "
            ::= { hwSiteActiveAlarmEntry 7 }

        hwSMUNetIdentifier OBJECT-TYPE
            SYNTAX OCTET STRING (SIZE (0..63))
            MAX-ACCESS read-only
            STATUS current
            DESCRIPTION
                "NE ID. It is of the character string type. It is the unique ID of the site (an independent network element (NE)) on the network. Otherwise, the configured character can not be any other languages except English."
            ::= { hwSiteActiveAlarmEntry 8 }

        hwSMUSiteDescription OBJECT-TYPE
            SYNTAX OCTET STRING (SIZE (0..63))
            MAX-ACCESS read-only
            STATUS current
            DESCRIPTION
                "Site description. It is of the character string type. It is used to describe the site information such as the site location, which users can configure.  Otherwise, the configured character can not be any other languages except English."
            ::= { hwSiteActiveAlarmEntry 9 }

        hwEquipId OBJECT-TYPE
            SYNTAX Unsigned32 (0..100)
            MAX-ACCESS read-only
            STATUS current
            DESCRIPTION
                "Equipment ID. Value range: 000,000 to 000,100, in which the first three digits indicate the device type and the last three digits indicate the device SN. "
            ::= { hwSiteActiveAlarmEntry 10 }

        hwEquipName OBJECT-TYPE
            SYNTAX OCTET STRING (SIZE (0..63))
            MAX-ACCESS read-only
            STATUS current
            DESCRIPTION
                "Equipment name. It is of the character string type, and users can set the name of the monitor. 
                Otherwise, the configured character can not be any other languages except English."
            ::= { hwSiteActiveAlarmEntry 11 }

        hwSiteAlarmTable OBJECT-TYPE
            SYNTAX SEQUENCE OF HwSiteAlarmEntry
            MAX-ACCESS not-accessible
             STATUS current
             DESCRIPTION
                "/"
            ::= { hwSiteAlarms 100 }

        hwSiteAlarmEntry OBJECT-TYPE
                        SYNTAX HwSiteAlarmEntry
            MAX-ACCESS not-accessible
             STATUS current
             DESCRIPTION
                "/"
            INDEX { hwAlarmIndex }
            ::= { hwSiteAlarmTable 1 }

        HwSiteAlarmEntry            ::= SEQUENCE {
                hwAlarmIndex
                    Unsigned32,
                hwAlarmText
                    OCTET STRING,
                hwAlarmLevel
                    INTEGER,
                hwAlarmSigDesc
                    OCTET STRING,
                hwAlarmRowStatus
                    RowStatus
            }

        hwAlarmIndex OBJECT-TYPE
            SYNTAX Unsigned32 (1..4294967295)
            MAX-ACCESS read-only
            STATUS current
            DESCRIPTION
                "Site alarm table index. It is the unique ID of the site alarm."
            ::= { hwSiteAlarmEntry 1 }

        hwAlarmText OBJECT-TYPE
            SYNTAX OCTET STRING (SIZE (0..63))
            MAX-ACCESS read-only
            STATUS current
            DESCRIPTION
                "Alarm name. It is of the character string type, and used to specify the content of a specific alarm.  "
            ::= { hwSiteAlarmEntry 2 }

        hwAlarmLevel OBJECT-TYPE
            SYNTAX INTEGER
                {
                critical(1),
                major(2),
                minor(3),
                warning(4),
                unknown(255)
                }
            MAX-ACCESS read-write
            STATUS current
            DESCRIPTION
                "Alarm level, which users can configure the alarm severity, is an enumeration type:
                  If the enumeration value is 1, it indicates a critical alarm;
                  If the enumeration value is 2, it indicates a major alarm;
                  If the enumeration value is 3, it indicates a minor alarm;
                  If the enumeration value is 4, it indicates a warning; "
            ::= { hwSiteAlarmEntry 3 }

        hwAlarmSigDesc OBJECT-TYPE
            SYNTAX OCTET STRING (SIZE (0..127))
            MAX-ACCESS read-only
            STATUS current
            DESCRIPTION
                "Alarm signal description. It is used to add and describe alarm content. Users can define the description of the alarm. 
                Otherwise, the configured character can not be any other languages except English."
            ::= { hwSiteAlarmEntry 4 }

        hwAlarmRowStatus OBJECT-TYPE
            SYNTAX RowStatus
            MAX-ACCESS read-create
            STATUS current
            DESCRIPTION
                "RowStatus of site alarms table."
            ::= { hwSiteAlarmEntry 100 }

        hwSiteMonitors OBJECT IDENTIFIER ::= { hwSiteMonitorMIBObjects 2 }

        hwMonitorsGroup OBJECT IDENTIFIER ::= { hwSiteMonitors 1 }

        hwMonsGroupId OBJECT-TYPE
            SYNTAX Unsigned32
            MAX-ACCESS read-only
            STATUS current
            DESCRIPTION
                "Site monitor group ID, is the unique ID of the site monitors."
            ::= { hwMonitorsGroup 1 }

        hwMonsGroupName OBJECT-TYPE
            SYNTAX OCTET STRING (SIZE (0..63))
            MAX-ACCESS read-write
            STATUS current
            DESCRIPTION
                "Site monitor group name is of the character string type, used to specify the monitor group. Users can configure it. Otherwise, the configured character can not be any other languages except English."
            ::= { hwMonitorsGroup 2 }

        hwMonsQuantity OBJECT-TYPE
            SYNTAX Unsigned32 (0..100)
            MAX-ACCESS read-only
            STATUS current
            DESCRIPTION
                "Total site intelligent monitors. Units:pcs."
            ::= { hwMonitorsGroup 3 }

        hwMonitor OBJECT IDENTIFIER ::= { hwSiteMonitors 2 }

        hwMonitorTable OBJECT-TYPE
            SYNTAX SEQUENCE OF HwMonitorEntry
            MAX-ACCESS not-accessible
             STATUS current
             DESCRIPTION
                "/"
            ::= { hwMonitor 1 }

        hwMonitorEntry OBJECT-TYPE
                        SYNTAX HwMonitorEntry
            MAX-ACCESS not-accessible
             STATUS current
             DESCRIPTION
                "/"
            INDEX { hwMonIndex }
            ::= { hwMonitorTable 1 }

        HwMonitorEntry            ::= SEQUENCE {
                hwMonIndex
                    Integer32,
                hwMonEquipId
                    Unsigned32,
                hwMonEquipName
                    OCTET STRING,
                hwMonEquipDescription
                    OCTET STRING,
                hwMonEquipSoftwareVersion
                    OCTET STRING,
                hwMonEquipManufacturer
                    OCTET STRING,
                hwSetMonEquipCtrlState
                    INTEGER,
                hwCtrlMonEquipReset
                    INTEGER,
                hwMonitorOperStatus
                    INTEGER,
                hwMonRowStatus
                    RowStatus
            }

        hwMonIndex OBJECT-TYPE
            SYNTAX Integer32 (1..100)
            MAX-ACCESS read-only
            STATUS current
            DESCRIPTION
                "Table index of the site monitors (hwSiteMonitorTable) is restricted by the quantity of the site monitors (hwMonsQuantity). 
                Value range: 1 to 100."
            ::= { hwMonitorEntry 1 }

        hwMonEquipId OBJECT-TYPE
            SYNTAX Unsigned32
            MAX-ACCESS read-only
            STATUS current
            DESCRIPTION
                "Site monitor ID. 
                Value range: 001,001 to 001,100, in which the first three digits indicate the device type and the last three digits indicate the device SN. "
            ::= { hwMonitorEntry 2 }

        hwMonEquipName OBJECT-TYPE
            SYNTAX OCTET STRING (SIZE (0..63))
            MAX-ACCESS read-write
            STATUS current
            DESCRIPTION
                "Monitor name. It is of the character string type, and users can set the name of the monitor.   
                Otherwise, the configured character can not be any other languages except English."
            ::= { hwMonitorEntry 3 }

        hwMonEquipDescription OBJECT-TYPE
            SYNTAX OCTET STRING (SIZE (0..63))
            MAX-ACCESS read-write
            STATUS current
            DESCRIPTION
                "Monitor description. It is of the character string type. Users can set the description of the monitor. 
                 Otherwise, the configured character can not be any other languages except English."
            ::= { hwMonitorEntry 4 }

        hwMonEquipSoftwareVersion OBJECT-TYPE
            SYNTAX OCTET STRING (SIZE (0..63))
            MAX-ACCESS read-only
            STATUS current
            DESCRIPTION
                "Monitor software version. It is of the character string type."
            ::= { hwMonitorEntry 5 }

        hwMonEquipManufacturer OBJECT-TYPE
            SYNTAX OCTET STRING (SIZE (0..63))
            MAX-ACCESS read-only
            STATUS current
            DESCRIPTION
                "Monitor manufacture. It is of the character string type, and is an inherent attribute of the device."
            ::= { hwMonitorEntry 7 }

        hwSetMonEquipCtrlState OBJECT-TYPE
            SYNTAX INTEGER
                {
                manualMode(1),
                autoMode(2),
                unknown(255)
                }
            MAX-ACCESS read-write
            STATUS current
            DESCRIPTION
                "Monitor control status. It is an enumeration type:
                  If the enumeration value is 1, it indicates the background control;
                  If the enumeration value is 2, it indicates the automatic control.
                  If the enumeration value is 255, it indicates monitor module operation status unknown. 
                  In manual state, monitor works under background commands; while monitors runs well automatically in auto state. 
                  For details, see the corresponding user manual of the monitor."
            ::= { hwMonitorEntry 11 }

        hwCtrlMonEquipReset OBJECT-TYPE
            SYNTAX INTEGER
                {
                normal(1),
                reset(2),
                unknown(255)
                }
            MAX-ACCESS read-write
            STATUS current
            DESCRIPTION
                "Warm-reset control of the monitor. It is an enumeration type:
                  If the enumeration value is 1, it indicates the Warm-reset control of the monitor is normal;
                  If the enumeration value is 2, it indicates the Warm-reset control of the monitor is reset.
                  If the enumeration value is 255, it indicates the Warm-reset control of the monito is unknown. "
            ::= { hwMonitorEntry 12 }

        hwMonitorOperStatus OBJECT-TYPE
            SYNTAX INTEGER
                {
                normal(1),
                commRs485Fail(2),
                commNetFail(3),
                fault(4),
                alarmResume(254),
                unknown(255)
                }
            MAX-ACCESS read-only
            STATUS current
            DESCRIPTION
                "State of the site monitor module. It is an enumeration type: 
                  If the enumeration value is 1, it indicates that the site monitor module is in the normal state;
                  If the enumeration value is 2, it indicates that the monitor module RS485 port communication failed; 
                  If the enumeration value is 3, it indicates that the monitor module net port communication failed;  
                  If the enumeration value is 4, it indicates that a fault occurs on the monitor module; 
                  If the enumeration value is 254, it indicates monitor module alarm resume;  
                  If the enumeration value is 255, it indicates monitor module operation status unknown. "
            ::= { hwMonitorEntry 99 }

        hwMonRowStatus OBJECT-TYPE
            SYNTAX RowStatus
            MAX-ACCESS read-create
            STATUS current
            DESCRIPTION
                "RowStatus of site monitor."
            ::= { hwMonitorEntry 100 }

        hwSiteRectifiers OBJECT IDENTIFIER ::= { hwSiteMonitorMIBObjects 3 }

        hwRectsGroup OBJECT IDENTIFIER ::= { hwSiteRectifiers 1 }

        hwRectsGroupId OBJECT-TYPE
            SYNTAX Unsigned32
            MAX-ACCESS read-only
            STATUS current
            DESCRIPTION
                "Device group ID of the rectifier module. It is the unique ID of the rectifier module group, and its default value: 002,000. 
                  The first digits indicate the device type and the last three digits indicate the device SN. If the last three digits are 000, it indicates a virtual device. "
            ::= { hwRectsGroup 1 }

        hwRectsGroupName OBJECT-TYPE
            SYNTAX OCTET STRING (SIZE (0..63))
            MAX-ACCESS read-write
            STATUS current
            DESCRIPTION
                "Name of the rectifier module group, character string type, is used to specify the rectifier module group. Users can configure it.  
                Otherwise, the configured character can not be any other languages except English."
            ::= { hwRectsGroup 2 }

        hwRectsTotalCurrent OBJECT-TYPE
            SYNTAX Unsigned32 (0..200000)
            MAX-ACCESS read-only
            STATUS current
            DESCRIPTION
                "Total current of the rectifier module group on the site. It indicates the real-time statistics of the rectifier module group on the site. 
                Default value: 0 to 20000, 
                units: A, 
                and the value is accurate to one decimal place (.1). 
                If the value is 2147483647(0x7FFFFFFF), it indicates that the value is invalid."
            ::= { hwRectsGroup 3 }

        hwRectsTotalQuantity OBJECT-TYPE
            SYNTAX Unsigned32 (0..256)
            MAX-ACCESS read-only
            STATUS current
            DESCRIPTION
                "Total quantity of the rectifier modules. 
                Value range: 0 to 256. Units:pcs."
            ::= { hwRectsGroup 4 }

        hwRectsRatedVoltage OBJECT-TYPE
            SYNTAX Unsigned32 (420..583)
            MAX-ACCESS read-only
            STATUS current
            DESCRIPTION
                "Rated voltage of the rectifier module group. It is an inherent attribute. 
                Value range: 42 to 58.3,
                Units: V, 
                and the value is accurate to one decimal place (.1). 
                 If the value is 2147483647(0x7FFFFFFF), it indicates that the value is invalid."
            ::= { hwRectsGroup 5 }

        hwModifyRectsOutputVoltage OBJECT-TYPE
            SYNTAX Unsigned32 (360..650)
            MAX-ACCESS read-write
            STATUS current
            DESCRIPTION
                "Voltage adjustment of the rectifier module, which users can configure it. 
                Value range: 36 to 65,
                Units: V, 
                and the value is accurate to one decimal space (.1). 
                Based on the actual requirements, users can modify the output voltage of the rectifier module by modifying the value of the node. 
                If the value is 2147483647(0x7FFFFFFF), it indicates that the value is invalid.
                NOTES: Be cautious about changing the value of the node.  Only the system in manual mode, this parameter can be configured successfully. If the setting returns an error, it means that the current setting value is not supported."
            ::= { hwRectsGroup 6 }

        hwSetRectsRedundEnable OBJECT-TYPE
            SYNTAX INTEGER
                {
                disable(1),
                enable(2),
                funcNotSupport(3)
                }
            MAX-ACCESS read-write
            STATUS current
            DESCRIPTION
                "Sleep function of the rectifier module group on the site. It is an enumeration value:
                If the NMS notifies the SNMP agent that this node is set to 1, it means to disable the sleep function of the rectifier module group;
                If the NMS notifies the SNMP agent that this node is set to 2, it means to enable the sleep function of the rectifier module group.
                If NMS get the node value is 3, it indicates that this function is not support, 
                and in such case the value set to the agent is invalid.
                Default value: to disable the sleep function of the rectifier module group. For details, see the corresponding user manual of the monitor."
            ::= { hwRectsGroup 7 }

        hwCtrlRectsAllOnOff OBJECT-TYPE
            SYNTAX INTEGER
                {
                on(1),
                off(2),
                nullOper(255)
                }
            MAX-ACCESS read-write
            STATUS current
            DESCRIPTION
                "Power-on or power-off of the rectifier module group (all the rectifier modules) on the site. It is an enumeration value:
                If the NMS notifies the SNMP agent that this node is set to 1, it indicates power-on of all rectifier modules;
                If the NMS notifies the SNMP agent that this node is set to 2, it indicates power-off of all the rectifier modules;
                If the NMS notifies the SNMP agent that this node is set to 255, it indicates nullOper of all the rectifier modules.
                NOTE: Only the system in manual mode, this parameter can be configured successfully."
            ::= { hwRectsGroup 8 }

        hwRectsTotalDCPower OBJECT-TYPE
            SYNTAX Unsigned32 (0..100000000)
            MAX-ACCESS read-only
            STATUS current
            DESCRIPTION
                "Total power of the direct current output.
                Value range: 0 to 100000000,
                units: W, 
                and the value is an integer.
                If the value is 2147483647(0x7FFFFFFF), it indicates that the value is invalid."
            ::= { hwRectsGroup 9 }

        hwRectsLoadUsage OBJECT-TYPE
            SYNTAX Unsigned32 (0..150)
            MAX-ACCESS read-only
            STATUS current
            DESCRIPTION
                "Load Usage.
                Value range: 0 to 150, 
                units: %, 
                and the value is an integer. 
                If the value is 2147483647(0x7FFFFFFF), it indicates that the value is invalid."
            ::= { hwRectsGroup 10 }

        hwRectsTotalACInputPower OBJECT-TYPE
            SYNTAX Unsigned32 (0..100000000)
            MAX-ACCESS read-only
            STATUS current
            DESCRIPTION
                "Total power of the direct current output. 
                Value range: 0 to 100000000, 
                units: W, 
                and the value is an integer. 
                If the value is 2147483647(0x7FFFFFFF), it indicates that the value is invalid."
            ::= { hwRectsGroup 11 }

        hwRectsHighRectifierCapacity OBJECT-TYPE
            SYNTAX Unsigned32 (0..150)
            MAX-ACCESS read-write
            STATUS current
            DESCRIPTION
                "High rectifier capacity. 
                Value range: 0 to 150, 
                units: %, 
                and the value is an integer. 
                If the value is 2147483647(0x7FFFFFFF), it indicates that the value is invalid."
            ::= { hwRectsGroup 12 }

        hwRectsLowRectifierCapacity OBJECT-TYPE
            SYNTAX Unsigned32 (0..150)
            MAX-ACCESS read-write
            STATUS current
            DESCRIPTION
                "Low rectifier capacity. 
                Value range: 0 to 150, 
                units: %, 
                and the value is an integer. 
                If the value is 2147483647(0x7FFFFFFF), it indicates that the value is invalid."
            ::= { hwRectsGroup 13 }

        hwRectsOverVoltProtThres OBJECT-TYPE
            SYNTAX Unsigned32 (560..605)
            MAX-ACCESS read-write
            STATUS current
            DESCRIPTION
                "Overvoltage protection threshold. 
                Value range: 56.0 to 60.5, 
                units: V, 
                and the value is accurate to one decimal space (.1). 
                If the value is 2147483647(0x7FFFFFFF), it indicates that the value is invalid."
            ::= { hwRectsGroup 14 }

        hwRectifier OBJECT IDENTIFIER ::= { hwSiteRectifiers 2 }

        hwRectConfigTable OBJECT-TYPE
            SYNTAX SEQUENCE OF HwRectConfigEntry
            MAX-ACCESS not-accessible
             STATUS current
             DESCRIPTION
                "Rectifier config information table. Use this table to get rectifiers equipment ID, software version, manufacturer, rated current, efficency, AC input type, and to control equipment on or off. 
                This table's index is hwRectConfigIndex, clone Rectifier config information table."
            ::= { hwRectifier 1 }

        hwRectConfigEntry OBJECT-TYPE
                        SYNTAX HwRectConfigEntry
            MAX-ACCESS not-accessible
             STATUS current
             DESCRIPTION
                "Rectifier config information table. Use this table to get rectifiers equipment ID, software version, manufacturer, rated current, efficency, AC input type, and to control equipment on or off. 
                This table's index is hwRectConfigIndex, clone Rectifier config information table."
            INDEX { hwRectConfigIndex }
            ::= { hwRectConfigTable 1 }

        HwRectConfigEntry            ::= SEQUENCE {
                hwRectConfigIndex
                    Integer32,
                hwRectEquipId
                    Unsigned32,
                hwRectEquipName
                    OCTET STRING,
                hwRectSoftwareVersion
                    OCTET STRING,
                hwRectSerialNo
                    OCTET STRING,
                hwRectRatedCurrent
                    Unsigned32,
                hwRectEfficency
                    Unsigned32,
                hwCtrlRectOnOff
                    INTEGER,
                hwRectConfigRowStatus
                    RowStatus
            }

        hwRectConfigIndex OBJECT-TYPE
            SYNTAX Integer32 (28672..30719)
            MAX-ACCESS read-only
            STATUS current
            DESCRIPTION
                "Index of the device configuration list for the rectifier modules, which value range: 28672to 30719(To the actual subject). Lines of the device list are restricted by the total quantity of the rectifier modules (hwRectsTotalQuantity)."
            ::= { hwRectConfigEntry 1 }

        hwRectEquipId OBJECT-TYPE
            SYNTAX Unsigned32
            MAX-ACCESS read-only
            STATUS current
            DESCRIPTION
                "Rectifier module ID. Value range: 002'001 to 002'255. The first digits indicate the device type and last three digits indicate the device SN. "
            ::= { hwRectConfigEntry 2 }

        hwRectEquipName OBJECT-TYPE
            SYNTAX OCTET STRING (SIZE (0..63))
            MAX-ACCESS read-only
            STATUS current
            DESCRIPTION
                "Device name of the rectifier module, character string type, is used to specify the rectifier module. Users can configure it.  
                Otherwise, the configured character can not be any other languages except English."
            ::= { hwRectConfigEntry 3 }

        hwRectSoftwareVersion OBJECT-TYPE
            SYNTAX OCTET STRING (SIZE (0..63))
            MAX-ACCESS read-only
            STATUS current
            DESCRIPTION
                "Software version of the rectifier module. It indicates the software version ID of the module. "
            ::= { hwRectConfigEntry 5 }

        hwRectSerialNo OBJECT-TYPE
            SYNTAX OCTET STRING (SIZE (0..127))
            MAX-ACCESS read-only
            STATUS current
            DESCRIPTION
                "Rectifier module SN. It indicates the electronic tag of the product."
            ::= { hwRectConfigEntry 8 }

        hwRectRatedCurrent OBJECT-TYPE
            SYNTAX Unsigned32 (0..2000)
            MAX-ACCESS read-only
            STATUS current
            DESCRIPTION
                "Rated voltage of the rectifier module, is an inherent attribute. 
                Value range: 0 to 200, Units: A, and the value is accurate to one decimal place (.1). If the value is 2147483647(0x7FFFFFFF), it indicates that the value is invalid. "
            ::= { hwRectConfigEntry 9 }

        hwRectEfficency OBJECT-TYPE
            SYNTAX Unsigned32 (0..1000)
            MAX-ACCESS read-only
            STATUS current
            DESCRIPTION
                "Efficiency of the rectifier module, is an inherent attribute. 
                Value range: 0 to 100, 
                Units: %, 
                and the value is accurate to one decimal place (.1). 
                If the value is 2147483647(0x7FFFFFFF), it indicates that the value is invalid."
            ::= { hwRectConfigEntry 10 }

        hwCtrlRectOnOff OBJECT-TYPE
            SYNTAX INTEGER
                {
                on(1),
                off(2),
                nullOper(255)
                }
            MAX-ACCESS read-write
            STATUS current
            DESCRIPTION
                "Power-on or power-off of the rectifier module, is an enumeration value. Users can modify the enumeration value of this node, thus controlling of the power-on or power-off of the rectifier module:
                  If the NMS notifies the SNMP agent that this node is set to 1, it indicates power-on of the rectifier module;
                  If the NMS notifies the SNMP agent that this node is set to 2, it indicates power-off of the rectifier module. "
            ::= { hwRectConfigEntry 12 }

        hwRectConfigRowStatus OBJECT-TYPE
            SYNTAX RowStatus
            MAX-ACCESS read-create
            STATUS current
            DESCRIPTION
                "RowStatus of rectifier config table."
            ::= { hwRectConfigEntry 100 }

        hwRectOperTable OBJECT-TYPE
            SYNTAX SEQUENCE OF HwRectOperEntry
            MAX-ACCESS not-accessible
             STATUS current
             DESCRIPTION
                "Rectifier runing information table. Use this table to get rectifiers output current, output voltage, totle runing time, and current run status. 
                This table's index is hwRectRunIndex, clone rectifier runing information table."
            ::= { hwRectifier 2 }

        hwRectOperEntry OBJECT-TYPE
                        SYNTAX HwRectOperEntry
            MAX-ACCESS not-accessible
             STATUS current
             DESCRIPTION
                "Rectifier runing information table. Use this table to get rectifiers output current, output voltage, totle runing time, and current run status. 
                This table's index is hwRectRunIndex, clone rectifier runing information table."
            INDEX { hwRectOperIndex }
            ::= { hwRectOperTable 1 }

        HwRectOperEntry            ::= SEQUENCE {
                hwRectOperIndex
                    Integer32,
                hwRectOutputCurrent
                    Unsigned32,
                hwRectOutputVoltage
                    Unsigned32,
                hwRectDCOutputPower
                    Unsigned32,
                hwRectACVoltage
                    Unsigned32,
                hwRectRatedEfficiency
                    Unsigned32,
                hwRectifierTemperature
                    Integer32,
                hwRectOperStatus
                    INTEGER,
                hwRectOperRowStatus
                    RowStatus
            }

        hwRectOperIndex OBJECT-TYPE
            SYNTAX Integer32 (28672..30719)
            MAX-ACCESS read-only
            STATUS current
            DESCRIPTION
                "Table index of the running rectifier modules, 
                which value range: 29672 to 30719(To the actual subject). 
                Lines of the device list are restricted by the total quantity of the rectifier modules (hwRectsTotalQuantity)."
            ::= { hwRectOperEntry 1 }

        hwRectOutputCurrent OBJECT-TYPE
            SYNTAX Unsigned32 (0..3000)
            MAX-ACCESS read-only
            STATUS current
            DESCRIPTION
                "Output current of the rectifier module. It is a real-time analog parameter. 
                Value range: 0 to 300, 
                Units: A, 
                and the value is accurate to one decimal place (.1). 
                If the value is 2147483647(0x7FFFFFFF), it indicates that the value is invalid."
            ::= { hwRectOperEntry 2 }

        hwRectOutputVoltage OBJECT-TYPE
            SYNTAX Unsigned32 (0..650)
            MAX-ACCESS read-only
            STATUS current
            DESCRIPTION
                "Output voltage of the rectifier module. It is a real-time analog parameter. 
                Value range: 0 to 65, 
                Units: V, 
                the value is accurate to one decimal place (.1). 
                If the value is 2147483647(0x7FFFFFFF), it indicates that the value is invalid. "
            ::= { hwRectOperEntry 3 }

        hwRectDCOutputPower OBJECT-TYPE
            SYNTAX Unsigned32 (0..30000)
            MAX-ACCESS read-only
            STATUS current
            DESCRIPTION
                "DC output power. 
                Value range: 0 to 30000, 
                units: W, 
                and the value is an integer.(1). 
                If the value is 2147483647(0x7FFFFFFF), it indicates that the value is invalid."
            ::= { hwRectOperEntry 5 }

        hwRectACVoltage OBJECT-TYPE
            SYNTAX Unsigned32 (0..6000)
            MAX-ACCESS read-only
            STATUS current
            DESCRIPTION
                "AC input voltage. 
                Value range: 0 to 600, 
                units: V, 
                and the value is accurate to one decimal space (.1).
                If the value is 2147483647(0x7FFFFFFF), it indicates that the value is invalid."
            ::= { hwRectOperEntry 6 }

        hwRectRatedEfficiency OBJECT-TYPE
            SYNTAX Unsigned32 (0..100)
            MAX-ACCESS read-only
            STATUS current
            DESCRIPTION
                "Rated Efficiency. 
                Value range: 0 to 100, 
                units: %, 
                and the value is an integer.(1). 
                If the value is 2147483647(0x7FFFFFFF), it indicates that the value is invalid."
            ::= { hwRectOperEntry 7 }

        hwRectifierTemperature OBJECT-TYPE
            SYNTAX Integer32 (-3000..3000)
            MAX-ACCESS read-only
            STATUS current
            DESCRIPTION
                "Rectifier Temperature. 
                Value range: -300 to 300, 
                units: degC, 
                and the value is accurate to one decimal space (.1). 
                If the value is 2147483647(0x7FFFFFFF), it indicates that the value is invalid."
            ::= { hwRectOperEntry 8 }

        hwRectOperStatus OBJECT-TYPE
            SYNTAX INTEGER
                {
                normal(1),
                fault(2),
                protect(3),
                commFail(4),
                switchOff(5),
                invalid(6),
                noConfig(7),
                acOff(8),
                rectLost(9),
                alarmResume(254),
                unknown(255)
                }
            MAX-ACCESS read-only
            STATUS current
            DESCRIPTION
                "State of the rectifier module. It is an enumeration type: 
                  If the enumeration value is 1, the rectifier module is in the normal state;
                  If the enumeration value is 2, a fault occurs on the rectifier module; 
                  If the enumeration value is 3, automatic protection of the rectifier module;
                  If the enumeration value is 4, communication of the rectifier module fails;
                  If the enumeration value is 5, the rectifier module is shut down; 
                  If the enumeration value is 6, the rectifier module is invalid; 
                  If the enumeration value is 7, this rectifier is not configured; 
                If the enumeration value is 8, this rectifier is ac off;
                If the enumeration value is 9, this rectifier is rectLost;
                  If the enumeration value is 254, rectifier alarm resume; 
                  If the enumeration value is 255, rectifier operation status unknown."
            ::= { hwRectOperEntry 99 }

        hwRectOperRowStatus OBJECT-TYPE
            SYNTAX RowStatus
            MAX-ACCESS read-create
            STATUS current
            DESCRIPTION
                "RowStatus of rectifier runing table."
            ::= { hwRectOperEntry 100 }

        hwSiteBatterys OBJECT IDENTIFIER ::= { hwSiteMonitorMIBObjects 4 }

        hwBattsConfig OBJECT IDENTIFIER ::= { hwSiteBatterys 1 }

        hwBattsGroupId OBJECT-TYPE
            SYNTAX Unsigned32
            MAX-ACCESS read-only
            STATUS current
            DESCRIPTION
                "Battery group ID. It is the unique ID of the battery group device. 
                The first digits indicate the device type and the last three digits indicate the device SN. 
                If the last three digits are 000, it indicates a virtual device. "
            ::= { hwBattsConfig 1 }

        hwBattsGroupName OBJECT-TYPE
            SYNTAX OCTET STRING (SIZE (0..63))
            MAX-ACCESS read-write
            STATUS current
            DESCRIPTION
                "Device name of the battery group. It is of the character string type, which can be configured by users. 
                Otherwise, the configured character can not be any other languages except English."
            ::= { hwBattsConfig 2 }

        hwBattsTotalQuantity OBJECT-TYPE
            SYNTAX Unsigned32 (0..100)
            MAX-ACCESS read-only
            STATUS current
            DESCRIPTION
                "Total quantity of battery strings, 
                which value range: 0 to 100. 
                Units:strings."
            ::= { hwBattsConfig 3 }

        hwSetBattsHighTempAction OBJECT-TYPE
            SYNTAX INTEGER
                {
                blvd(1),
                lowerDcOutput(2),
                disable(255)
                }
            MAX-ACCESS read-write
            STATUS current
            DESCRIPTION
                "Battery high-temperature protection mode. It is an enumeration value, and can be configured. 
                If the enumeration value is 1, it indicates the power-off protection mode;
                If the enumeration value is 2, it indicates the protection mode of lowering the output voltage of the rectifier module. 
                If the enumeration value is 255, it indicates do nothing. "
            ::= { hwBattsConfig 4 }

        hwSetBattsHighTempVoltLimit OBJECT-TYPE
            SYNTAX Unsigned32 (420..530)
            MAX-ACCESS read-write
            STATUS current
            DESCRIPTION
                "Battery protection voltage under high temperature. It works with the low-voltage power-off protection in battery high-temperature protection mode, which can be configured by users. 
                If the low-voltage power-off protection mode (that is, the enumeration value is 1) is selected, the node is a low-voltage power-off node. 
                Value range: 42 to 53, 
                units: V, 
                and the value is accurate to one decimal place (.1).  
                If the value is 2147483647(0x7FFFFFFF), it indicates that the value is invalid."
            ::= { hwBattsConfig 5 }

        hwSetBattsHTDLimit OBJECT-TYPE
            SYNTAX Integer32 (25..80)
            MAX-ACCESS read-write
            STATUS current
            DESCRIPTION
                "Upper threshold of the battery high temperature disconnection(HTD), can be configured by users. 
                Value range: 25 to 80, 
                Units: centigrade (degC), 
                and the value is an integer (1). 
                If the value is 2147483647(0x7FFFFFFF), it indicates that the value is invalid.
                NOTE: There is linkage between hwSetBattsHTDLimit and hwSetBattsTempUpperLimit"
            ::= { hwBattsConfig 6 }

        hwSetBattsHTDEnable OBJECT-TYPE
            SYNTAX INTEGER
                {
                enable(1),
                disable(2)
                }
            MAX-ACCESS read-write
            STATUS current
            DESCRIPTION
                "Battery high temperature disconnection enable. It is an enumeration type:
                  If the enumeration value is 1, enable the operation of the battery disconnection in high temperature; 
                  If the enumeration value is 2, disable the operation of the battery disconnection in high temperature. 
                  The operation of the battery disconnection in high temperature is disabled by default. "
            ::= { hwBattsConfig 7 }

        hwSetBattsFloatVoltage OBJECT-TYPE
            SYNTAX Unsigned32 (420..580)
            MAX-ACCESS read-write
            STATUS current
            DESCRIPTION
                "Float charge voltage of the batteries, can be configured by users. 
                Value range: 42 to 58, 
                units: V, 
                and the value is accurate to one decimal place (.1) 
                If the value is 2147483647(0x7FFFFFFF), it indicates that the value is invalid.
                NOTE: There is linkage between hwSetBattsFloatVoltage and hwSetBattsBoostVoltage
                "
            ::= { hwBattsConfig 8 }

        hwSetBattsBoostVoltage OBJECT-TYPE
            SYNTAX Unsigned32 (420..580)
            MAX-ACCESS read-write
            STATUS current
            DESCRIPTION
                "Boostcharge voltage of the batteries, can be configured by users. 
                Value range: 42 to 58, 
                units: V, 
                and the value is accurate to one decimal place (.1). 
                If the value is 2147483647(0x7FFFFFFF), it indicates that the value is invalid.
                NOTE: There is linkage between hwSetBattsFloatVoltage and hwSetBattsBoostVoltage"
            ::= { hwBattsConfig 9 }

        hwSetBattsCurrLimitCoefficient OBJECT-TYPE
            SYNTAX Unsigned32 (5..50)
            MAX-ACCESS read-write
            STATUS current
            DESCRIPTION
                "Current-limiting point coefficient of the batteries, can be configured by users. 
                Value range: 0.05 to 0.5, 
                units: C10, 
                and the value is accurate to two decimal places (.01). 
                If the value is 2147483647(0x7FFFFFFF), it indicates that the value is invalid.
                There is linkage between  hwSetBattsChargeOvercurAlmThreshold and  hwSetBattsCurrLimitCoefficient.
                Current-limiting point coefficient must be less than or equal to the charge overcurrent alarm threshold."
            ::= { hwBattsConfig 10 }

        hwSetBattsCompFactor OBJECT-TYPE
            SYNTAX Unsigned32 (0..150)
            MAX-ACCESS read-write
            STATUS current
            DESCRIPTION
                "Temperature compensated coefficient of the batteries, can be configured by user. 
                Value range: 0 to 150, 
                units: mv per centigrade, 
                and the value is an integer (1). 
                If the value is 2147483647(0x7FFFFFFF), it indicates that the value is invalid."
            ::= { hwBattsConfig 11 }

        hwCtrlBattsBoostFloat OBJECT-TYPE
            SYNTAX INTEGER
                {
                floatCharge(1),
                boostCharge(2),
                nullOper(255)
                }
            MAX-ACCESS read-write
            STATUS current
            DESCRIPTION
                "Control batteries charge mode between boost and float. It is an enumeration value. 
                  Users actively control the conversion. 
                  If the NMS notifies the SNMP agent that this node is set to 1, it means to start the float charge mode of the batteries; 
                  If the NMS notifies the SNMP agent that this node is set to 2, it means to start the boost charge mode of the batteries. 
                  If the NMS notifies the SNMP agent that this node is set to 255, it means to start the mode of the batteries is nullOper. "
            ::= { hwBattsConfig 12 }

        hwSetBattsRatedCapacity OBJECT-TYPE
            SYNTAX Unsigned32 (5..10000)
            MAX-ACCESS read-write
            STATUS current
            DESCRIPTION
                "Set batteries rated capacity. It is an analog parameter collected by the battery string in real time.
                Value range: 5 to 10000, 
                units: Ah, 
                the value is an integer (1). 
                If the value is 2147483647(0x7FFFFFFF), it indicates that the value is invalid."
            ::= { hwBattsConfig 13 }

        hwSetBattsTimedBoostChargeEnabled OBJECT-TYPE
            SYNTAX INTEGER
                {
                disable(1),enable(2),unknown(255)
                }
            MAX-ACCESS read-write
            STATUS current
            DESCRIPTION
                "Timed Boost Charge Enabled. It is an enumeration value, and can be configured. 
                If the enumeration value is 1, it indicates timed boost charge is disabled;
                If the enumeration value is 2, it indicates timed boost charge is enabled. 
                If the enumeration value is 255, it indicates timed boost charge is unknown. "
            ::= { hwBattsConfig 14 }

        hwSetBattsTimedBoostChargePeriod OBJECT-TYPE
            SYNTAX Unsigned32 (1..365)
            MAX-ACCESS read-write
            STATUS current
            DESCRIPTION
                "Timed Boost Charge Interval. 
                Value range: 1 to 365, 
                units: Day, 
                and the value is an integer.(1). 
                If the value is 2147483647(0x7FFFFFFF), it indicates that the value is invalid."
            ::= { hwBattsConfig 15 }

        hwSetBattsMaxTimedBCDuration OBJECT-TYPE
            SYNTAX Unsigned32 (1..24)
            MAX-ACCESS read-write
            STATUS current
            DESCRIPTION
                "Maximum Timed Boost Charge Duration. 
                Value range: 1 to 24, 
                units: h, 
                and the value is an integer.(1). 
                If the value is 2147483647(0x7FFFFFFF), it indicates that the value is invalid."
            ::= { hwBattsConfig 16 }

        hwSetBattsChargeOvercurAlmThreshold OBJECT-TYPE
            SYNTAX Unsigned32 (5..100)
            MAX-ACCESS read-write
            STATUS current
            DESCRIPTION
                "Charge Overcurrent Alarm Threshold. 
                Value range: 0.05 to 1, 
                units: C10, 
                and the value is accurate to two decimal space (.01). 
                If the value is 2147483647(0x7FFFFFFF), it indicates that the value is invalid.
                There is linkage between  hwSetBattsChargeOvercurAlmThreshold and  hwSetBattsCurrLimitCoefficient.
                Current-limiting point coefficient must be less than or equal to the charge overcurrent alarm threshold."
            ::= { hwBattsConfig 17 }

        hwSetBattsLowCapacityAlarmThreshold OBJECT-TYPE
            SYNTAX Unsigned32 (0..90)
            MAX-ACCESS read-write
            STATUS current
            DESCRIPTION
                "Low Capacity Alarm Threshold. 
                Value range: 0 to 90, 
                units: %, 
                and the value is an integer. (1)
                If the value is 2147483647(0x7FFFFFFF), it indicates that the value is invalid."
            ::= { hwBattsConfig 18 }

        hwBattsOperate OBJECT IDENTIFIER ::= { hwSiteBatterys 2 }

        hwBattsTotalCurrent OBJECT-TYPE
            SYNTAX Integer32 ( -4000000..4000000)
            MAX-ACCESS read-only
            STATUS current
            DESCRIPTION
                "Total current of the battery group. It indicates the real-time statistics of the battery group on the site. 
                Value range: -400000 to +400000, 
                units: A, 
                and the value is accurate to one decimal place (.1).  
                If the value is 2147483647(0x7FFFFFFF), it indicates that the value is invalid."
            ::= { hwBattsOperate 1 }

        hwBattsPreDischargeTime OBJECT-TYPE
            SYNTAX Unsigned32 (0..15360)
            MAX-ACCESS read-only
            STATUS current
            DESCRIPTION
                "Battery group backup time. It indicates the real-time statistics of the battery group. 
                Value range: 0 to 15360, 
                Units: minutes (min),  
                and the value is an integer (1).  
                If the value is 2147483647(0x7FFFFFFF), it indicates that the value is invalid."
            ::= { hwBattsOperate 2 }

        hwBattsChargeStatus OBJECT-TYPE
            SYNTAX INTEGER
                {
                floatCharge(1),
                boostCharge(2),
                disCharge(3),
                hibernating(4),
                offline(7),
                unknown(255)
                }
            MAX-ACCESS read-only
            STATUS current
            DESCRIPTION
                "Battery charging state, indicates the charging and discharging information about the battery group. It is an enumeration type. 
                If the enumeration value is 1, it indicates a battery group in the float charging state. 
                If the enumeration value is 2, it indicates a battery group in the boost charging state. 
                If the enumeration value is 3, it indicates a battery group in the discharging state. 
                If the enumeration value is 4, it indicates a battery group in the hibernating state.
                If the enumeration value is 7, it indicates a battery group in the Offline state.
                If the enumeration value is 7, it indicates a battery group in the Offline state. "
            ::= { hwBattsOperate 3 }

        hwBattsCurrLimitStatus OBJECT-TYPE
            SYNTAX INTEGER
                {
                unlimited(1),
                limited(2),
                unknown(255)
                }
            MAX-ACCESS read-only
            STATUS current
            DESCRIPTION
                "Battery group current-limiting state, indicates the state information about the battery group. It is an enumeration value. 
                  If the enumeration value is 1, it indicates that the current of the battery group is not limited. 
                  If the enumeration value is 2, it indicates the current of the battery group is limited.
                  If the enumeration value is 2, it indicates the current of the battery group is unknown. "
            ::= { hwBattsOperate 4 }

        hwBattsTemprature1 OBJECT-TYPE
            SYNTAX Integer32 ( -300..200)
            MAX-ACCESS read-only
            STATUS current
            DESCRIPTION
                "Battery temperature. It is a battery parameter collected in real time. 
                Value range: -300 to 200, 
                unit: centigrade (degC), 
                and the value is an integer .
                If the value is 2147483647(0x7FFFFFFF), it indicates that battery temperature sensor is not configured."
            ::= { hwBattsOperate 5 }

        hwBattsRatedCapacity OBJECT-TYPE
            SYNTAX Unsigned32 (0..2147483647)
            MAX-ACCESS read-only
            STATUS current
            DESCRIPTION
                "Batteries actual capacity. 
                It is an analog parameter collected by the battery string in real time.
                Value range: 0 to 2147483647, 
                units: Ah, 
                the value is an integer (1).  
                If the value is 2147483647(0x7FFFFFFF), it indicates that the value is invalid."
            ::= { hwBattsOperate 8 }

        hwBattsRemainCapacity OBJECT-TYPE
            SYNTAX Unsigned32 (0..2147483647)
            MAX-ACCESS read-only
            STATUS current
            DESCRIPTION
                "Remaining capacity of all of the battery. 
                It is an analog parameter collected by the battery string in real time. 
                Value range: 0 to 2147483647, 
                units: Ah, 
                and the value is an integer (1).  
                If the value is 2147483647(0x7FFFFFFF), it indicates that the value is invalid."
            ::= { hwBattsOperate 9 }

        hwTotalRemainingCapacityPercent OBJECT-TYPE
            SYNTAX Unsigned32 (0..100)
            MAX-ACCESS read-only
            STATUS current
            DESCRIPTION
                "Total Remaining Capacity Percent. 
                Value range: 0 to 100, units: %, 
                and the value is an integer.(1). 
                If the value is 2147483647(0x7FFFFFFF), it indicates that the value is invalid."
            ::= { hwBattsOperate 10 }

        hwBattsTest OBJECT IDENTIFIER ::= { hwSiteBatterys 3 }

        hwSetBattsManuStdTestTime OBJECT-TYPE
            SYNTAX Unsigned32 (1..6000)
            MAX-ACCESS read-write
            STATUS current
            DESCRIPTION
                "Battery standard test time, It can be configured by users,
                value range defines between 1 to 6000, 
                units: minutes(min).  
                and its value is an integer (1). 
                Here, if battery manual test is standard mode, 
                If the value is 2147483647(0x7FFFFFFF), it indicates that the value is invalid."
            ::= { hwBattsTest 2 }

        hwSetBattsManuShortTestTime OBJECT-TYPE
            SYNTAX Unsigned32 (1..240)
            MAX-ACCESS read-write
            STATUS current
            DESCRIPTION
                "Battery short test time, It can be configured by users,
                value range defines between 1 to 240,  
                units: minutes(min).
                and its value is an integer (1).
                If battery manual test is simple mode,  
                If the value is 2147483647(0x7FFFFFFF), it indicates that the value is invalid."
            ::= { hwBattsTest 5 }

        hwSetBattsManuShortTestEndVolt OBJECT-TYPE
            SYNTAX Unsigned32 (442..530)
            MAX-ACCESS read-write
            STATUS current
            DESCRIPTION
                "Voltage when the battery short test is ended, can be configured by users. Here, if battery manual test is standard mode, 
                value range defines between 44.2 to 53, 
                Units: V, 
                and the value is accurate to one decimal place (.1). 
                If the value is 2147483647(0x7FFFFFFF), it indicates that the value is invalid."
            ::= { hwBattsTest 6 }

        hwCtrlBattsTestStartStop OBJECT-TYPE
            SYNTAX INTEGER
                {
                stdTestStart(1),
                shortTestStart(2),
                testStop(3),
                nullOper(255)
                }
            MAX-ACCESS read-write
            STATUS current
            DESCRIPTION
                "Battery manualtest start and stop. It is an enumeration value. 
                  If the value is 1, it means to start a standard manual test; 
                  If the value is 2, it means to start a short manual test; 
                  If the value is 3, it means to stop the battery test.
                If the value is 255, it means null operate(can't set to smu);  
                  Set the parameters, such as battery test time, and voltage when the battery test stops before the node controls the start of the battery test. If the parameters are not set this time, the system uses the configuration parameters by default; and if the battery test is started at the first time, the system uses the default value. 
                  Battery test can only start up in some conditions, so that the reason of Start of battery short test failed may be as follow:
                  1. Interval between this test and the latest AC outage or test is longer than the preset duration.
                  2. No major alarm is raised.
                  3. The number of healthy modules is greater than 0.
                  4. The number of battery strings is greater than 0."
            ::= { hwBattsTest 7 }

        hwBattsTestResultTable OBJECT-TYPE
            SYNTAX SEQUENCE OF HwBattsTestResultEntry
            MAX-ACCESS not-accessible
             STATUS current
             DESCRIPTION
                "Battery test result record table. 
                Use this table to get battery test inital time, test result, battery efficiency, battery discharge time, terminated voltage, average current, discharge AH value, test temperature and test terminated course. 
                This table's index is hwBattsTestResultIndex, clone Battery test result record table."
            ::= { hwBattsTest 100 }

        hwBattsTestResultEntry OBJECT-TYPE
                        SYNTAX HwBattsTestResultEntry
            MAX-ACCESS not-accessible
             STATUS current
             DESCRIPTION
                "Battery test result record table. 
                Use this table to get battery test inital time, test result, battery efficiency, battery discharge time, terminated voltage, average current, discharge AH value, test temperature and test terminated course. 
                This table's index is hwBattsTestResultIndex, clone Battery test result record table."
            INDEX { hwBattsTestResultIndex }
            ::= { hwBattsTestResultTable 1 }

        HwBattsTestResultEntry            ::= SEQUENCE {
                hwBattsTestResultIndex
                    Integer32,
                hwBattsTestType
                    INTEGER,
                hwBattsTestStartTime
                    OCTET STRING,
                hwBattsTestResult
                    INTEGER,
                hwBattsEfficiency
                    Integer32,
                hwBattsDischargeTime
                    Unsigned32,
                hwBattsDischargeEndVoltage
                    Unsigned32,
                hwBattsDischargeAvCurrent
                    Integer32,
                hwBattsDischargeAhValue
                    Unsigned32,
                hwBattsTestTemperature
                    Integer32,
                hwBattsTestEndCourse
                    INTEGER,
                hwBattsTestResultRowStatus
                    RowStatus
            }

        hwBattsTestResultIndex OBJECT-TYPE
            SYNTAX Integer32 (1..100)
            MAX-ACCESS read-only
            STATUS current
            DESCRIPTION
                "Table index of the battery test results. Currently up to 10 times of the battery test results are saved by default. "
            ::= { hwBattsTestResultEntry 1 }

        hwBattsTestType OBJECT-TYPE
            SYNTAX INTEGER
                {
                manualTest(1),
                acOffAutoTest(2),
                timedTest(3),
                shortTest(4),
                unknown(255)
                }
            MAX-ACCESS read-only
            STATUS current
            DESCRIPTION
                "Record test type of the battery test. It is an enumeration value: 
                  If the NMS notifies the SNMP agent that this node is set to 1, it indicates a manual test; 
                  If the NMS notifies the SNMP agent that this node is set to 2, it indicates a simplified test;
                  If the NMS notifies the SNMP agent that this node is set to 3, it indicates a timed test;
                  If the NMS notifies the SNMP agent that this node is set to 4, it indicates a short test;
                  If the NMS notifies the SNMP agent that this node is set to 255, it indicates a other test."
            ::= { hwBattsTestResultEntry 2 }

        hwBattsTestStartTime OBJECT-TYPE
            SYNTAX OCTET STRING (SIZE (0..127))
            MAX-ACCESS read-only
            STATUS current
            DESCRIPTION
                "Test start time of the record in the battery test. It is of the character string type."
            ::= { hwBattsTestResultEntry 3 }

        hwBattsTestResult OBJECT-TYPE
            SYNTAX INTEGER
                {
                battNoResult(1),
                battNormal(2),
                battPreAlarm(3),
                battAlarm(4),
                unknown(255)
                }
            MAX-ACCESS read-only
            STATUS current
            DESCRIPTION
                "Battery test result. It is an enumeration value.
                  If the enumeration value of the node is 1, it indicates that the battery test has no result: 
                  If the enumeration value of the node is 2, it indicates that the battery is in the normal state: 
                  If the enumeration value of the node is 3, it indicates that the battery is in the minor abnormal state, 
                  If the enumeration value of the node is 4, it indicates that the battery is in the alarm state,
                  If the enumeration value of the node is 255, it indicates that the battery state is unknown,"
            ::= { hwBattsTestResultEntry 4 }

        hwBattsEfficiency OBJECT-TYPE
            SYNTAX Integer32 (0..100)
            MAX-ACCESS read-only
            STATUS current
            DESCRIPTION
                "Battery efficiency test. 
                Value range: 0 to 100, 
                Units: %, 
                and the value is an integer (1).
                  If the value is -1, it indicates that the test value is inefficient.
                  If the value is 255, it indicates that the test value is invalid."
            ::= { hwBattsTestResultEntry 5 }

        hwBattsDischargeTime OBJECT-TYPE
            SYNTAX Unsigned32 (0..10000)
            MAX-ACCESS read-only
            STATUS current
            DESCRIPTION
                "Discharge time of the battery test records. 
                Value range: 0 to 100, 
                units: hour (h), 
                and the value is accurate to two decimal places (.01).  
                If the value is 2147483647(0x7FFFFFFF), it indicates that the value is invalid."
            ::= { hwBattsTestResultEntry 6 }

        hwBattsDischargeEndVoltage OBJECT-TYPE
            SYNTAX Unsigned32 (0..600)
            MAX-ACCESS read-only
            STATUS current
            DESCRIPTION
                "Discharge termination voltage of the battery test. 
                Value range: 0 to 60, 
                units: V, 
                and the value is accurate to one decimal place (.1).  
                If the value is 2147483647(0x7FFFFFFF), it indicates that the value is invalid."
            ::= { hwBattsTestResultEntry 7 }

        hwBattsDischargeAvCurrent OBJECT-TYPE
            SYNTAX Integer32 ( -10000..10000)
            MAX-ACCESS read-only
            STATUS current
            DESCRIPTION
                "Average discharge current of the battery test. 
                Value range: -1000 to 1000, 
                units: A, 
                and the value is accurate to one decimal place (.1).  
                If the value is 2147483647(0x7FFFFFFF), it indicates that the value is invalid."
            ::= { hwBattsTestResultEntry 8 }

        hwBattsDischargeAhValue OBJECT-TYPE
            SYNTAX Unsigned32 (0..5000)
            MAX-ACCESS read-only
            STATUS current
            DESCRIPTION
                "Discharge ampere per hour the battery test. 
                Value range: 0 to 5000, 
                Units: Ah, 
                and the value is an integer (1).   
                If the value is 2147483647(0x7FFFFFFF), it indicates that the value is invalid."
            ::= { hwBattsTestResultEntry 9 }

        hwBattsTestTemperature OBJECT-TYPE
            SYNTAX Integer32 ( -50..100)
            MAX-ACCESS read-only
            STATUS current
            DESCRIPTION
                "Battery temperature of the battery test termination. 
                Value range: -50 to +100, 
                Units: centigrade (degC), 
                and the value is an integer (1). 
                If the value is -1024, it indicates that no battery temperature value sensor is detected."
            ::= { hwBattsTestResultEntry 10 }

        hwBattsTestEndCourse OBJECT-TYPE
            SYNTAX INTEGER
                {
                voltageToEnd(1),
                timeToEnd(2),
                acOnToEnd(3),
                manulToEnd(4),
                faultAlarmToEnd(5),
                lowCapacityToEnd(6),
                lowTempToEnd(7),
                unknown(255)
                }
            MAX-ACCESS read-only
            STATUS current
            DESCRIPTION
                "Termination factors of the battery test. It is an enumeration value. 
                  If the enumeration value is 1, it indicates that the voltage value of the battery test reaches the set termination voltage; 
                  If the enumeration value is 2, it indicates that the voltage value of the battery test reaches the timing limit; 
                  If the enumeration value is 3, it indicates that an alarm related to the battery leads to the stop of the battery test; 
                  If the enumeration value is 4, it indicates that a battery test is stopped manually,
                  If the enumeration value is 5, it indicates that battery fault alarm happened,
                If the enumeration value is 6, it indicates that battery low capacity happened,
                If the enumeration value is 7, it indicates that battery low temp happened,
                  If the enumeration value is 255, it indicates that battery test end for other courses."
            ::= { hwBattsTestResultEntry 11 }

        hwBattsTestResultRowStatus OBJECT-TYPE
            SYNTAX RowStatus
            MAX-ACCESS read-create
            STATUS current
            DESCRIPTION
                "RowStatus of battery test table."
            ::= { hwBattsTestResultEntry 100 }

        hwSetBattsConsCurrTestEnable OBJECT-TYPE
            SYNTAX INTEGER
                {
                disable(1),
                enable(2)
                }
            MAX-ACCESS read-write
            STATUS current
            DESCRIPTION
                "Battery constant current test function enable or disable. It is an enumeration value. 
                  If the value is 1, it means the function is disabled; 
                  If the value is 2, it means the function is enabled."
            ::= { hwBattsTest 8 }

        hwSetBattsConsCurrTestDischCurrent OBJECT-TYPE
            SYNTAX Unsigned32 (1..9999)
            MAX-ACCESS read-write
            STATUS current
            DESCRIPTION
                "The battery discharge current in the constant current test. 
                It is an integer value(range:1A~9999A) and the value is accurate to 1A."
            ::= { hwBattsTest 9 }

        hwSetBattsTimeTestMode OBJECT-TYPE
            SYNTAX INTEGER
                {
                disable(1),scheduledTest(3)
                }
            MAX-ACCESS read-write
            STATUS current
            DESCRIPTION
                "Battery constant current test function enable or disable. 
                It is an enumeration value.
                If the value is 1, it means to disable the timed test of battery; 
                If the value is 3, it means to enable the scheduled test of battery."
            ::= { hwBattsTest 10 }

        hwSetBattsScheduledTestPeriod OBJECT-TYPE
            SYNTAX Unsigned32 (2..999)
            MAX-ACCESS read-write
            STATUS current
            DESCRIPTION
                "Scheduled Test Period. 
                Value range: 2 to 999, 
                units: Day, 
                and the value is an integer.(1). 
                If the value is 2147483647(0x7FFFFFFF), it indicates that the value is invalid."
            ::= { hwBattsTest 11 }

        hwSetBattsTestEndCapacity OBJECT-TYPE
            SYNTAX Unsigned32 (0..99)
            MAX-ACCESS read-write
            STATUS current
            DESCRIPTION
                "Test End Capacity.  
                Value range: 0 to 99, 
                units: %, 
                and the value is an integer. 
                If the value is 2147483647(0x7FFFFFFF), it indicates that the value is invalid."
            ::= { hwBattsTest 12 }

        hwSetBattsTestEndTemperature OBJECT-TYPE
            SYNTAX Integer32 (-5..15)
            MAX-ACCESS read-write
            STATUS current
            DESCRIPTION
                "Test End Temperature. 
                Value range: -5 to 15, 
                units: degC, 
                and the value is an integer.(1). 
                If the value is 2147483647(0x7FFFFFFF), it indicates that the value is invalid."
            ::= { hwBattsTest 13 }

        hwSetBattsShortTestEnable OBJECT-TYPE
            SYNTAX INTEGER
                {
                disable(1),enable(2)
                }
            MAX-ACCESS read-write
            STATUS current
            DESCRIPTION
                "Battery short test enable.
                It is an enumeration value, and can be configured. 
                If the enumeration value is 1, it indicates battery short test is disabled;
                If the enumeration value is 2, it indicates battery short test is enabled. "
            ::= { hwBattsTest 14 }

        hwSetBattsShortTestPeriod OBJECT-TYPE
            SYNTAX Unsigned32 (1..360)
            MAX-ACCESS read-write
            STATUS current
            DESCRIPTION
                "Short Test Period. 
                Value range: 1 to 360, 
                units: Day, 
                and the value is an integer.(1). 
                If the value is 2147483647(0x7FFFFFFF), it indicates that the value is invalid."
            ::= { hwBattsTest 15 }

        hwBattString OBJECT IDENTIFIER ::= { hwSiteBatterys 4 }

        hwBattStringConfigTable OBJECT-TYPE
            SYNTAX SEQUENCE OF HwBattStringConfigEntry
            MAX-ACCESS not-accessible
             STATUS current
             DESCRIPTION
                "Battery string config table. Use this table to get battery string equipment ID and equipment name, to set battery standard capacity and battery install time as well. This table's index is hwBattStringConfigIndex, clone battery string config table."
            ::= { hwBattString 1 }

        hwBattStringConfigEntry OBJECT-TYPE
                        SYNTAX HwBattStringConfigEntry
            MAX-ACCESS not-accessible
             STATUS current
             DESCRIPTION
                "Battery string config table. Use this table to get battery string equipment ID and equipment name, to set battery standard capacity and battery install time as well. This table's index is hwBattStringConfigIndex, clone battery string config table."
            INDEX { hwBattStringConfigIndex }
            ::= { hwBattStringConfigTable 1 }

        HwBattStringConfigEntry            ::= SEQUENCE {
                hwBattStringConfigIndex
                    Integer32,
                hwBattStringEquipId
                    Unsigned32,
                hwBattStringEquipName
                    OCTET STRING,
                hwSetBattsTempUpperLimit
                    Integer32,
                hwSetBattsTempLowerLimit
                    Integer32,
                hwSetBattStdCapacity
                    Integer32,
                hwBattStringConfigRowStatus
                    RowStatus
            }

        hwBattStringConfigIndex OBJECT-TYPE
            SYNTAX Integer32 (1..100)
            MAX-ACCESS read-only
            STATUS current
            DESCRIPTION
                "Device table index of the battery string,
                value range: 1 to 100(To the actual subject)."
            ::= { hwBattStringConfigEntry 1 }

        hwBattStringEquipId OBJECT-TYPE
            SYNTAX Unsigned32 (3001..3100)
            MAX-ACCESS read-only
            STATUS current
            DESCRIPTION
                "Batteries device ID, can be configured by users. Value range: 003,001 to 003,100, in which the first three digits specify the device type and the last three specify the device SN."
            ::= { hwBattStringConfigEntry 2 }

        hwBattStringEquipName OBJECT-TYPE
            SYNTAX OCTET STRING (SIZE (0..63))
            MAX-ACCESS read-only
            STATUS current
            DESCRIPTION
                "Batteries device name, of the character string type, is used to specify the batteries. Users can configure it. Otherwise, the configured character can not be any other languages except English."
            ::= { hwBattStringConfigEntry 3 }

        hwSetBattsTempUpperLimit OBJECT-TYPE
            SYNTAX Integer32 ( 25..80)
            MAX-ACCESS read-write
            STATUS current
            DESCRIPTION
                "Upper threshold of the battery temperature alarm, can be configured by users. 
                Value range: 25 to 80, 
                Units: centigrade (degC), 
                and the value is an integer (1).  
                If the value is 2147483647(0x7FFFFFFF), it indicates that the value is invalid.
                NOTE: There is linkage between hwSetBattsHTDLimit and hwSetBattsTempUpperLimit"
            ::= { hwBattStringConfigEntry 4 }

        hwSetBattsTempLowerLimit OBJECT-TYPE
            SYNTAX Integer32 ( -20..20)
            MAX-ACCESS read-write
            STATUS current
            DESCRIPTION
                "Lower threshold of the battery temperature alarm, can be configured by users. 
                Value range: -20 to 20, 
                Units: centigrade (degC), 
                and the value is an integer (1).  
                If the value is 2147483647(0x7FFFFFFF), it indicates that the value is invalid."
            ::= { hwBattStringConfigEntry 5 }

        hwSetBattStdCapacity OBJECT-TYPE
            SYNTAX Integer32 (5..10000)
            MAX-ACCESS read-write
            STATUS current
            DESCRIPTION
                "Set battery standard capacity, is an inherent attribute of the device. 
                Value range: 5 to 10000, 
                units: Ah, 
                the value is an integer (1).   
                If the value is 2147483647(0x7FFFFFFF), it indicates that the value is invalid."
            ::= { hwBattStringConfigEntry 8 }

        hwBattStringConfigRowStatus OBJECT-TYPE
            SYNTAX RowStatus
            MAX-ACCESS read-create
            STATUS current
            DESCRIPTION
                "RowStatus of battery string config table."
            ::= { hwBattStringConfigEntry 100 }

        hwBattStringOperTable OBJECT-TYPE
            SYNTAX SEQUENCE OF HwBattStringOperEntry
            MAX-ACCESS not-accessible
             STATUS current
             DESCRIPTION
                "Battery string runing table. Use this table to get battery string current, persent of remain capacity, battery remain capacity, battery actual capacity, as well as  battery temperature. 
                This table's index is hwBattStringRunIndex, clone battery string runing table."
            ::= { hwBattString 2 }

        hwBattStringOperEntry OBJECT-TYPE
                        SYNTAX HwBattStringOperEntry
            MAX-ACCESS not-accessible
             STATUS current
             DESCRIPTION
                "Battery string runing table. Use this table to get battery string current, persent of remain capacity, battery remain capacity, battery actual capacity, as well as  battery temperature. 
                This table's index is hwBattStringRunIndex, clone battery string runing table."
            INDEX { hwBattStringOperIndex }
            ::= { hwBattStringOperTable 1 }

        HwBattStringOperEntry            ::= SEQUENCE {
                hwBattStringOperIndex
                    Integer32,
                hwBattStringCurrent
                    Integer32,
                hwBattStringRemainCapacityPercent
                    Unsigned32,
                hwBattStringRemainCapacity
                    Unsigned32,
                hwBattStringTemprature
                    Integer32,
                hwBattStringMidpointVoltage
                    Integer32,
                hwBattStringOperStatus
                    INTEGER,
                hwBattStringOperRowStatus
                    RowStatus
            }

        hwBattStringOperIndex OBJECT-TYPE
            SYNTAX Integer32 (1..100)
            MAX-ACCESS read-only
            STATUS current
            DESCRIPTION
                "Device table index of the battery string, 
                which value range: 1 to 100(To the actual subject)."
            ::= { hwBattStringOperEntry 1 }

        hwBattStringCurrent OBJECT-TYPE
            SYNTAX Integer32 ( -10000..10000)
            MAX-ACCESS read-only
            STATUS current
            DESCRIPTION
                "Batteries current. It is an analog parameter collected by the battery string in real time. 
                Value range: -1000 to +1000, 
                units: A, 
                and the value is accurate to one decimal place (.1).  
                If the value is 2147483647(0x7FFFFFFF), it indicates that the value is invalid."
            ::= { hwBattStringOperEntry 2 }

        hwBattStringRemainCapacityPercent OBJECT-TYPE
            SYNTAX Unsigned32 (0..1000)
            MAX-ACCESS read-only
            STATUS current
            DESCRIPTION
                "Remaining capacity percentage of the battery string. 
                Value range: 0 to 100, 
                units: %, 
                and the value is accurate to one decimal place (.1).  
                If the value is 2147483647(0x7FFFFFFF), it indicates that the value is invalid."
            ::= { hwBattStringOperEntry 3 }

        hwBattStringRemainCapacity OBJECT-TYPE
            SYNTAX Unsigned32 (0..10000)
            MAX-ACCESS read-only
            STATUS current
            DESCRIPTION
                "Remaining capacity of the battery string. It is an analog parameter collected by the battery string in real time. 
                Value range: 0 to 10000, 
                units: Ah, 
                and the value is an integer (1).  
                If the value is 2147483647(0x7FFFFFFF), it indicates that the value is invalid."
            ::= { hwBattStringOperEntry 4 }

        hwBattStringTemprature OBJECT-TYPE
            SYNTAX Integer32 ( -3000..2000)
            MAX-ACCESS read-only
            STATUS current
            DESCRIPTION
                "Battery temperature. It is a battery parameter collected in real time. 
                Value range: -300 to +200, 
                unit: centigrade (degC), 
                and the value is accurate to one decimal place (.1).
                If the value is 2147483647(0x7FFFFFFF), it indicates that battery temperature sensor is not configured."
            ::= { hwBattStringOperEntry 6 }

        hwBattStringMidpointVoltage OBJECT-TYPE
            SYNTAX Integer32 ( -900..900)
            MAX-ACCESS read-only
            STATUS current
            DESCRIPTION
                "Batteries midpoint voltage. It is an analog parameter collected by the battery string in real time. 
                Value range: -90 to +90, 
                unit: V, 
                and the value is accurate to one decimal place (.1)."
            ::= { hwBattStringOperEntry 7 }

        hwBattStringOperStatus OBJECT-TYPE
            SYNTAX INTEGER
                {
                normal(1),
                tempHigh(2),
                tempLow(3),
                loopBreak(4),
                overCurrent(5),
                unbalance(6),
                discharge(7),
                fuseBreak(8),
                alarmResume(254),
                unknown(255)
                }
            MAX-ACCESS read-only
            STATUS current
            DESCRIPTION
                "State of the site battery string module. It is an enumeration type: 
                  If the enumeration value is 1, it indicates that the site battery string is in the normal state; 
                  If the enumeration value is 2, it indicates that the battery string is over upper alarm threshold of temperature; 
                  If the enumeration value is 3, it indicates that the battery string is under lower alarm threshold of temperature;  
                  If the enumeration value is 4, it indicates that battery string loop has disconnected;  
                  If the enumeration value is 5, it indicates that the current of batery is over upper charging threshold;
                  If the enumeration value is 6, it indicates that the battery string is unbalance;  
                  If the enumeration value is 7, it indicates that battery string is discharge;  
                  If the enumeration value is 8, it indicates that battery string is fuseBreak;
                  If the enumeration value is 254, it indicates battery string alarm resume; 
                  If the enumeration value is 255, it indicates battery string operation status unknown. "
            ::= { hwBattStringOperEntry 99 }

        hwBattStringOperRowStatus OBJECT-TYPE
            SYNTAX RowStatus
            MAX-ACCESS read-create
            STATUS current
            DESCRIPTION
                "RowStatus of battery string runing table."
            ::= { hwBattStringOperEntry 100 }

        hwSiteAcDistributions OBJECT IDENTIFIER ::= { hwSiteMonitorMIBObjects 5 }

        hwAcDistributionsGroup OBJECT IDENTIFIER ::= { hwSiteAcDistributions 1 }

        hwAcsGroupId OBJECT-TYPE
            SYNTAX Unsigned32
            MAX-ACCESS read-only
            STATUS current
            DESCRIPTION
                "AC group ID, is the unique ID of the AC group. The first three digits indicate the device type and the last three indicate the device SN. If the last three digits are 000, it indicates a virtual device. "
            ::= { hwAcDistributionsGroup 1 }

        hwAcsGroupName OBJECT-TYPE
            SYNTAX OCTET STRING (SIZE (0..63))
            MAX-ACCESS read-write
            STATUS current
            DESCRIPTION
                "Device name of the AC group. It is of the character string type, and can be configured by users. Otherwise, the configured character can not be any other languages except English."
            ::= { hwAcDistributionsGroup 2 }

        hwAcsTotalCurrent OBJECT-TYPE
            SYNTAX Unsigned32 (0..10000)
            MAX-ACCESS read-only
            STATUS current
            DESCRIPTION
                "Total current of the AC group. It indicates the real-time statistics of the AC group. 
                Value range: 0 to 1000, 
                units: A, 
                and the value is accurate to one decimal place (.1). 
                If the value is 2147483647(0x7FFFFFFF), it indicates that the value is invalid."
            ::= { hwAcDistributionsGroup 3 }

        hwAcsInputQuantity OBJECT-TYPE
            SYNTAX Unsigned32 (0..100)
            MAX-ACCESS read-only
            STATUS current
            DESCRIPTION
                "Total quantity of the site ACUs. Value range: 0 to 100. "
            ::= { hwAcDistributionsGroup 4 }

        hwSetAcsUpperVoltLimit OBJECT-TYPE
            SYNTAX Unsigned32 (60..300)
            MAX-ACCESS read-write
            STATUS current
            DESCRIPTION
                "Upper threshold of the AC voltage alarm, can be configured by users. 
                Value range: 60 to300, 
                units: V, 
                and the value is an integer (1).  
                If the value is 2147483647(0x7FFFFFFF), it indicates that the value is invalid.
                NOTE: There is linkage between hwSetAcsUpperVoltLimit and hwSetAcsLowerVoltLimit"
            ::= { hwAcDistributionsGroup 5 }

        hwSetAcsLowerVoltLimit OBJECT-TYPE
            SYNTAX Unsigned32 (60..300)
            MAX-ACCESS read-write
            STATUS current
            DESCRIPTION
                "Lower threshold of the AC voltage alarm, can be configured by users. 
                Value range: 60 to 300, 
                units: V, 
                and the value is an integer (1).  
                If the value is 2147483647(0x7FFFFFFF), it indicates that the value is invalid.
                NOTE: There is linkage between hwSetAcsUpperVoltLimit and hwSetAcsLowerVoltLimit"
            ::= { hwAcDistributionsGroup 6 }

        hwAcsPowerConsumption OBJECT-TYPE
            SYNTAX Unsigned32 (0..1000000)
            MAX-ACCESS read-only
            STATUS current
            DESCRIPTION
                "hwAcsPowerConsumption of the AC. Value range:0 to 10000, units:KWh ,the value is accurate to two decimal place (.01). If the value is 2147483647(0x7FFFFFFF), it indicates that the value is invalid."
            ::= { hwAcDistributionsGroup 7 }

        hwAcDistribution OBJECT IDENTIFIER ::= { hwSiteAcDistributions 2 }

        hwAcInputTable OBJECT-TYPE
            SYNTAX SEQUENCE OF HwAcInputEntry
            MAX-ACCESS not-accessible
             STATUS current
             DESCRIPTION
                "AC input table. Use this table to get AC distribution unit ID, AC distribution unit name, A phase or AB line voltage, B phase or BC line voltage, C phase or CA line voltage, AC input breaker status, 
                as well as AC output breakers quantity, which defines hwAcOutputBreakerTable row number. This table's index is hwAcInputIndex, clone AC input table."
            ::= { hwAcDistribution 1 }

        hwAcInputEntry OBJECT-TYPE
                        SYNTAX HwAcInputEntry
            MAX-ACCESS not-accessible
             STATUS current
             DESCRIPTION
                "AC input table. Use this table to get AC distribution unit ID, AC distribution unit name, A phase or AB line voltage, B phase or BC line voltage, C phase or CA line voltage, AC input breaker status, 
                as well as AC output breakers quantity, which defines hwAcOutputBreakerTable row number. This table's index is hwAcInputIndex, clone AC input table."
            INDEX { hwAcInputIndex }
            ::= { hwAcInputTable 1 }

        HwAcInputEntry            ::= SEQUENCE {
                hwAcInputIndex
                    Integer32,
                hwAcEquipId
                    Unsigned32,
                hwAcEquipName
                    OCTET STRING,
                hwApOrAblVoltage
                    Unsigned32,
                hwBpOrBclVoltage
                    Unsigned32,
                hwCpOrCalVoltage
                    Unsigned32,
                hwAphaseCurrent
                    Integer32,
                hwBphaseCurrent
                    Integer32,
                hwCphaseCurrent
                    Integer32,
                hwAcInputOperStatus
                    INTEGER,
                hwAcRowStatus
                    RowStatus
            }

        hwAcInputIndex OBJECT-TYPE
            SYNTAX Integer32 (1..100)
            MAX-ACCESS read-only
            STATUS current
            DESCRIPTION
                "ACU device table index, 
                which value range: 1 to 100. 
                Lines of the device list are restricted by the total quantity of ACUs (hwAcsInputQuantity)."
            ::= { hwAcInputEntry 1 }

        hwAcEquipId OBJECT-TYPE
            SYNTAX Unsigned32
            MAX-ACCESS read-only
            STATUS current
            DESCRIPTION
                "ACU device ID, which users can configure. Value range: 004,001 to 004,100, 
                in which The first digits indicate the device type and the last three digits indicate the device SN."
            ::= { hwAcInputEntry 2 }

        hwAcEquipName OBJECT-TYPE
            SYNTAX OCTET STRING (SIZE (0..63))
            MAX-ACCESS read-write
            STATUS current
            DESCRIPTION
                "ACU device name, of the character string type, is used to specify the alternating current unit (ACU). 
                Users can configure it. Otherwise, the configured character can not be any other languages except English."
            ::= { hwAcInputEntry 3 }

        hwApOrAblVoltage OBJECT-TYPE
            SYNTAX Unsigned32 (0..6000)
            MAX-ACCESS read-only
            STATUS current
            DESCRIPTION
                "ACU A-phase or AB-line voltage. 
                Value range: 0 to 600, 
                units: V, 
                and the value is accurate to one decimal place (.1).  
                If the value is 2147483647(0x7FFFFFFF), it indicates that the value is invalid."
            ::= { hwAcInputEntry 4 }

        hwBpOrBclVoltage OBJECT-TYPE
            SYNTAX Unsigned32 (0..6000)
            MAX-ACCESS read-only
            STATUS current
            DESCRIPTION
                "ACU B-phase or BC-line voltage. 
                Value range: 0 to 600, 
                units: V, 
                and the value is accurate to one decimal place (.1).  
                If the value is 2147483647(0x7FFFFFFF), it indicates that the value is invalid."
            ::= { hwAcInputEntry 5 }

        hwCpOrCalVoltage OBJECT-TYPE
            SYNTAX Unsigned32 (0..6000)
            MAX-ACCESS read-only
            STATUS current
            DESCRIPTION
                "ACU C-phase or CA-line voltage. 
                Value range: 0 to 600, 
                units: V, 
                and the value is accurate to one decimal place (.1).  
                If the value is 2147483647(0x7FFFFFFF), it indicates that the value is invalid."
            ::= { hwAcInputEntry 6 }

        hwAphaseCurrent OBJECT-TYPE
            SYNTAX Integer32 (0..200000)
            MAX-ACCESS read-only
            STATUS current
            DESCRIPTION
                "ACU A-phase current. It is an analog parameter collected by the ACU in real time. 
                Value range: 0 to 20000, 
                units: A, 
                and the value is accurate to one decimal place (.1).  
                If the value is 2147483647(0x7FFFFFFF), it indicates that the value is invalid."
            ::= { hwAcInputEntry 7 }

        hwBphaseCurrent OBJECT-TYPE
            SYNTAX Integer32 (0..200000)
            MAX-ACCESS read-only
            STATUS current
            DESCRIPTION
                "ACU B-phase current. It is an analog parameter collected by the ACU in real time. 
                Value range: 0 to 20000, 
                units: A, 
                and the value is accurate to one decimal place (.1). 
                If the value is 2147483647(0x7FFFFFFF), it indicates that the value is invalid."
            ::= { hwAcInputEntry 8 }

        hwCphaseCurrent OBJECT-TYPE
            SYNTAX Integer32 (0..200000)
            MAX-ACCESS read-only
            STATUS current
            DESCRIPTION
                "ACU C-phase current. It is an analog parameter collected by the ACU in real time. 
                Value range: 0 to 20000, 
                units: A, 
                and the value is accurate to one decimal place (.1).  
                If the value is 2147483647(0x7FFFFFFF), it indicates that the value is invalid."
            ::= { hwAcInputEntry 9 }

        hwAcInputOperStatus OBJECT-TYPE
            SYNTAX INTEGER
                {
                normal(1),
                acOff(2),
                acAbsent(3),
                voltHigh(4),
                voltLow(5),
                freqHigh(6),
                freqLow(7),
                alarmResume(254),
                unknown(255)
                }
            MAX-ACCESS read-only
            STATUS current
            DESCRIPTION
                "State of the site AC distribution uint. It is an enumeration type: 
                  If the enumeration value is 1, it indicates that the site AC distribution uint is in the normal state; 
                  If the enumeration value is 2, it indicates that AC distribution uint power off; 
                  If the enumeration value is 3, it indicates that AC input phase absent;
                  If the enumeration value is 4, it indicates that AC voltage is over upper alarm threshold;  
                  If the enumeration value is 5, it indicates that AC voltage is under lower alarm threshold;  
                  If the enumeration value is 6, it indicates that AC voltage is freqHigh;  
                  If the enumeration value is 7, it indicates that AC voltage is freqLow;  
                  If the enumeration value is 254, it indicates AC distribution uint alarm resume; 
                  If the enumeration value is 255, it indicates AC distribution uint operation status unknown. "
            ::= { hwAcInputEntry 99 }

        hwAcRowStatus OBJECT-TYPE
            SYNTAX RowStatus
            MAX-ACCESS read-create
            STATUS current
            DESCRIPTION
                "RowStatus of ACU."
            ::= { hwAcInputEntry 100 }

        hwSiteDcDistributions OBJECT IDENTIFIER ::= { hwSiteMonitorMIBObjects 6 }

        hwDcDistributionsGroup OBJECT IDENTIFIER ::= { hwSiteDcDistributions 1 }

        hwDcsGroupId OBJECT-TYPE
            SYNTAX Unsigned32
            MAX-ACCESS read-only
            STATUS current
            DESCRIPTION
                "DC group ID: unique ID of the DC group. in which The first digits indicate the device type and the last three digits indicate the device SN. If the last three digits are 000, it indicates a virtual device."
            ::= { hwDcDistributionsGroup 1 }

        hwDcsGroupName OBJECT-TYPE
            SYNTAX OCTET STRING (SIZE (0..63))
            MAX-ACCESS read-write
            STATUS current
            DESCRIPTION
                "Device name of the DC group, of the character string type, can be configured by users. Otherwise, the configured character can not be any other languages except English."
            ::= { hwDcDistributionsGroup 2 }

        hwDcsTotalVoltage OBJECT-TYPE
            SYNTAX Unsigned32 (0..1000)
            MAX-ACCESS read-only
            STATUS current
            DESCRIPTION
                "Total voltage of the DC group. 
                Value range: 0 to 100, 
                units: V, 
                and the value is accurate to one decimal place (.1).  
                If the value is 2147483647(0x7FFFFFFF), it indicates that the value is invalid."
            ::= { hwDcDistributionsGroup 3 }

        hwDcsTotalCurrent OBJECT-TYPE
            SYNTAX Integer32 ( -300000..300000)
            MAX-ACCESS read-only
            STATUS current
            DESCRIPTION
                "Total current of the DC group. 
                Value range: -30000 to 30000, 
                units: A, 
                and the value is accurate to one decimal place (.1).   
                If the value is 2147483647(0x7FFFFFFF), it indicates that the value is invalid."
            ::= { hwDcDistributionsGroup 4 }

        hwDcsTotalPower OBJECT-TYPE
            SYNTAX Unsigned32 (0..3000000)
            MAX-ACCESS read-only
            STATUS current
            DESCRIPTION
                "Total power of the DC group. 
                Value range: 0 to 3000000, 
                units: W, 
                and the value is an integer (1).  
                If the value is 2147483647(0x7FFFFFFF), it indicates that the value is invalid."
            ::= { hwDcDistributionsGroup 5 }

        hwDcsTotalQuantity OBJECT-TYPE
            SYNTAX Unsigned32 (0..100)
            MAX-ACCESS read-only
            STATUS current
            DESCRIPTION
                "Total quantity of the DC units, and its Value range: 0 to 100."
            ::= { hwDcDistributionsGroup 6 }

        hwSetDcsUpperVoltLimit OBJECT-TYPE
            SYNTAX Unsigned32 (530..600)
            MAX-ACCESS read-write
            STATUS current
            DESCRIPTION
                "Upper threshold of the DC voltage alarm, can be configued by users. 
                Value range: 53 to 60, 
                units: V, 
                and the value is accurate to one decimal space (.1).  
                If the value is 2147483647(0x7FFFFFFF), it indicates that the value is invalid.
                NOTE: There is linkage between hwSetDcsUpperVoltLimit and hwSetDcsLowerVoltLimit"
            ::= { hwDcDistributionsGroup 7 }

        hwSetDcsLowerVoltLimit OBJECT-TYPE
            SYNTAX Unsigned32 (350..570)
            MAX-ACCESS read-write
            STATUS current
            DESCRIPTION
                "Lower threshold of the DC voltage alarm, can be configued by users. 
                Value range: 35 to 57, 
                units: V, 
                and the value is accurate to one decimal space (.1).  
                If the value is 2147483647(0x7FFFFFFF), it indicates that the value is invalid.
                NOTE: There is linkage between hwSetDcsUpperVoltLimit and hwSetDcsLowerVoltLimit"
            ::= { hwDcDistributionsGroup 8 }

        hwDcsPerfoLoadConsume OBJECT-TYPE
            SYNTAX Unsigned32 (0..429467295)
            MAX-ACCESS read-only
            STATUS current
            DESCRIPTION
                "PerfoLoad Consume of the DC,
                Value range:  0 to 429467295, 
                units: KWh, 
                and the value is an integer (1).
                If the value is 2147483647(0x7FFFFFFF), it indicates that the value is invalid."
            ::= { hwDcDistributionsGroup 9 }

        hwDcDistribution OBJECT IDENTIFIER ::= { hwSiteDcDistributions 2 }

        hwDcOutputTable OBJECT-TYPE
            SYNTAX SEQUENCE OF HwDcOutputEntry
            MAX-ACCESS not-accessible
             STATUS current
             DESCRIPTION
                "/"
            ::= { hwDcDistribution 1 }

        hwDcOutputEntry OBJECT-TYPE
                        SYNTAX HwDcOutputEntry
            MAX-ACCESS not-accessible
             STATUS current
             DESCRIPTION
                "/"
            INDEX { hwDcOutputIndex }
            ::= { hwDcOutputTable 1 }

        HwDcOutputEntry            ::= SEQUENCE {
                hwDcOutputIndex
                    Integer32,
                hwDcOutputEquipId
                    Unsigned32,
                hwDcOutputEquipName
                    OCTET STRING,
                hwDcOutputVoltage
                    Unsigned32,
                hwDcOutputCurrent
                    Integer32,
                hwDcOutputPower
                    Unsigned32,
                hwLoadsQuantity
                    Unsigned32,
                hwLoadUsage
                    Unsigned32,
                hwDcOutputOperStatus
                    INTEGER,
                hwDcOutputRowStatus
                    RowStatus
            }

        hwDcOutputIndex OBJECT-TYPE
            SYNTAX Integer32 (1..100)
            MAX-ACCESS read-only
            STATUS current
            DESCRIPTION
                "Device table index of the DC units, which value range: 1 to 100. Lines of the device list are restricted by the total quantity of DC units (hwDcsQuantity)."
            ::= { hwDcOutputEntry 1 }

        hwDcOutputEquipId OBJECT-TYPE
            SYNTAX Unsigned32 (6001..6100)
            MAX-ACCESS read-only
            STATUS current
            DESCRIPTION
                "DC unit device ID, which value range: 006,001 to 006,100. The first digits indicate the device type and the last three digits indicate the device SN. "
            ::= { hwDcOutputEntry 2 }

        hwDcOutputEquipName OBJECT-TYPE
            SYNTAX OCTET STRING (SIZE (0..63))
            MAX-ACCESS read-write
            STATUS current
            DESCRIPTION
                "DC unit device name, of the character string type, can be configued by users.  Otherwise, the configured character can not be any other languages except English."
            ::= { hwDcOutputEntry 3 }

        hwDcOutputVoltage OBJECT-TYPE
            SYNTAX Unsigned32 (0..1000)
            MAX-ACCESS read-only
            STATUS current
            DESCRIPTION
                "DC output voltage. It is an analog parameter collected by the DC power in real time. 
                Value range: 0 to 100, 
                units: V, 
                and the value is accurate to one decimal space (.1).  
                If the value is 2147483647(0x7FFFFFFF), it indicates that the value is invalid."
            ::= { hwDcOutputEntry 4 }

        hwDcOutputCurrent OBJECT-TYPE
            SYNTAX Integer32 ( -300000..300000)
            MAX-ACCESS read-only
            STATUS current
            DESCRIPTION
                "DC output current. It is an analog parameter collected by the DC power in real time. 
                Value range: -30000 to 30000, 
                units: A, 
                and the value is accurate to one decimal space (.1). 
                If the value is 2147483647(0x7FFFFFFF), it indicates that the value is invalid."
            ::= { hwDcOutputEntry 5 }

        hwDcOutputPower OBJECT-TYPE
            SYNTAX Unsigned32 (0..3000000)
            MAX-ACCESS read-only
            STATUS current
            DESCRIPTION
                "DC output power. It is an analog parameter collected by the DC power in real time. 
                Value range: 0 to 3000000, 
                units: W, 
                and the value is an integer (1).  
                If the value is 2147483647(0x7FFFFFFF), it indicates that the value is invalid."
            ::= { hwDcOutputEntry 6 }

        hwLoadsQuantity OBJECT-TYPE
            SYNTAX Unsigned32 (0..100)
            MAX-ACCESS read-only
            STATUS current
            DESCRIPTION
                "Quantity of the DC load output branches, 
                which value range: 0 to 100.  
                As the DC unit lower-level subset, the node indicates the quantity of the DC load output branches contained by each DC unit lower-level subset."
            ::= { hwDcOutputEntry 7 }

        hwLoadUsage OBJECT-TYPE
            SYNTAX Unsigned32 (0..100)
            MAX-ACCESS read-only
            STATUS current
            DESCRIPTION
                "The load usage of rated rectifier capacity. 
                Value range: 0 to 100, 
                units: %, 
                and the value is an integer (1)."
            ::= { hwDcOutputEntry 8 }

        hwDcOutputOperStatus OBJECT-TYPE
            SYNTAX INTEGER
                {
                normal(1),
                voltHigh(2),
                voltLow(3),
                dcAbsent(4),
                overload(5),
                alarmResume(254),
                unknown(255)
                }
            MAX-ACCESS read-only
            STATUS current
            DESCRIPTION
                "State of the site DC distribution uint. It is an enumeration type: 
                If the enumeration value is 1, it indicates that the site DC distribution uint is in the normal state; 
                If the enumeration value is 2, it indicates that DC voltage is over the upper alarm threshold;
                If the enumeration value is 3, it indicates that DC voltage is under the lower alarm threshold; 
                If the enumeration value is 4, it indicates that DC voltage is dcAbsent; 
                If the enumeration value is 5, it indicates that DC voltage is overload; 
                If the enumeration value is 254, it indicates DC distribution uint alarm resume; 
                If the enumeration value is 255, it indicates DC distribution uint operation status unknown. "
            ::= { hwDcOutputEntry 99 }

        hwDcOutputRowStatus OBJECT-TYPE
            SYNTAX RowStatus
            MAX-ACCESS read-create
            STATUS current
            DESCRIPTION
                "RowStatus of Dc output equipments."
            ::= { hwDcOutputEntry 100 }

        hwLvdUnits OBJECT IDENTIFIER ::= { hwSiteMonitorMIBObjects 7 }

        hwLvdsGroup OBJECT IDENTIFIER ::= { hwLvdUnits 1 }

        hwLvdsGroupId OBJECT-TYPE
            SYNTAX Unsigned32
            MAX-ACCESS read-only
            STATUS current
            DESCRIPTION
                "LVD unit group ID. It is the unique ID of the LVD unit group. The first digits indicate the device type. The last three digits indicate the device SN. If the last three digits are 000, it indicates a virtual device."
            ::= { hwLvdsGroup 1 }

        hwLvdsGroupName OBJECT-TYPE
            SYNTAX OCTET STRING (SIZE (0..63))
            MAX-ACCESS read-write
            STATUS current
            DESCRIPTION
                "Low-voltage power-off unit group name, of the character string type, can be configured by users.
                Otherwise, the configured character can not be any other languages except English."
            ::= { hwLvdsGroup 2 }

        hwLvdsTotalQuantity OBJECT-TYPE
            SYNTAX Unsigned32 (0..100)
            MAX-ACCESS read-only
            STATUS current
            DESCRIPTION
                "Total quantity of power-off units. Value range: 0 to 100."
            ::= { hwLvdsGroup 3 }

        hwLvdUnit OBJECT IDENTIFIER ::= { hwLvdUnits 2 }

        hwLvdBranchTable OBJECT-TYPE
            SYNTAX SEQUENCE OF HwLvdBranchEntry
            MAX-ACCESS not-accessible
             STATUS current
             DESCRIPTION
                "Power-off unit table. Use this table to get Lvd unit equipment ID and power-off unit equipment name, set power-off enable and power-off voltage, as well as control power-off unit disconnected. This table's index is hwLvdBranchIndex, which qualificated by hwLvdsQuantity, clone power-off unit table."
            ::= { hwLvdUnit 1 }

        hwLvdBranchEntry OBJECT-TYPE
                        SYNTAX HwLvdBranchEntry
            MAX-ACCESS not-accessible
             STATUS current
             DESCRIPTION
                "Power-off unit table. Use this table to get Lvd unit equipment ID and power-off unit equipment name, set power-off enable and power-off voltage, as well as control power-off unit disconnected. This table's index is hwLvdBranchIndex, which qualificated by hwLvdsQuantity, clone power-off unit table."
            INDEX { hwLvdBranchIndex }
            ::= { hwLvdBranchTable 1 }

        HwLvdBranchEntry            ::= SEQUENCE {
                hwLvdBranchIndex
                    Integer32,
                hwLvdUnitEquipId
                    Unsigned32,
                hwLvdUnitEquipName
                    OCTET STRING,
                hwSetLvdEnable
                    INTEGER,
                hwSetLvdVoltage
                    Integer32,
                hwSetLvdMode
                    INTEGER,
                hwSetLvdReconnectedVoltage
                    Integer32,
                hwSetLvdDisconnectedTime
                    Integer32,
                hwSetLvdDisconnectedCapacity
                    Integer32,
                hwLvdBranchOperStatus
                    INTEGER,
                hwLvdBranchRowStatus
                    RowStatus
            }

        hwLvdBranchIndex OBJECT-TYPE
            SYNTAX Integer32 (1..100)
            MAX-ACCESS read-only
            STATUS current
            DESCRIPTION
                "Device table index of a power-off unit. 
                Value range: 1 to 100. Lines of the device list are restricted by the total quantity of the power-off units (hwLvdsTotalQuantity). "
            ::= { hwLvdBranchEntry 1 }

        hwLvdUnitEquipId OBJECT-TYPE
            SYNTAX Unsigned32 (8001..8100)
            MAX-ACCESS read-only
            STATUS current
            DESCRIPTION
                "Device ID of a power-off unit. Value range: 8001 to 8100. The first digits indicate the device type and the last three digits indicate the device SN. "
            ::= { hwLvdBranchEntry 2 }

        hwLvdUnitEquipName OBJECT-TYPE
            SYNTAX OCTET STRING (SIZE (0..63))
            MAX-ACCESS read-only
            STATUS current
            DESCRIPTION
                "Device name of a power-off unit, of the character string type, is used to specify the low-voltage power-off unit. Users can configure it. Otherwise, the configured character can not be any other languages except English. "
            ::= { hwLvdBranchEntry 3 }

        hwSetLvdEnable OBJECT-TYPE
            SYNTAX INTEGER
                {
                enabled(1),
                disabled(2)
                }
            MAX-ACCESS read-write
            STATUS current
            DESCRIPTION
                "Control power-off unit enabling. It is an enumeration value, and users actively set it. 
                  If the enumeration value is 1, it means to enable the power-off unit; 
                  If the enumeration value is 2, it means to disable the power-off unit. 
                  When the power-off unit control is not configured, the power-off unit is enabled by default."
            ::= { hwLvdBranchEntry 4 }

        hwSetLvdVoltage OBJECT-TYPE
            SYNTAX Integer32 (350..560)
            MAX-ACCESS read-write
            STATUS current
            DESCRIPTION
                "Low-voltage power-off voltage of a power-off unit can be configured by users. 
                Its value range: 35 to 56, 
                units: V, 
                and the value is accurate to one decimal space (.1).  
                If the value is 2147483647(0x7FFFFFFF), it indicates that the value is invalid.
                NOTE: There is linkage between hwSetLvdVoltage and hwSetLvdReconnectedVoltage"
            ::= { hwLvdBranchEntry 5 }

        hwSetLvdMode OBJECT-TYPE
            SYNTAX INTEGER
                {
                byVoltage(1),
                byTime(2),
                byCapacity(3),
                unknown(255)
                }
            MAX-ACCESS read-write
            STATUS current
            DESCRIPTION
                "Select the control mode of the power-off unit. It is an enumeration value, users can configure it manually. 
                    If the NMS notifies the SNMP agent that the node is set to 1, it means to select the voltage power off mode; 
                    If the NMS notifies the SNMP agent that the node is set to 2, it means to select the time power off mode;  
                    If the NMS notifies the SNMP agent that the node is set to 3, it means to select the capacity power off mode;
                    If the NMS notifies the SNMP agent that the node is set to 255, it means to select the capacity power unknown mode;"
            ::= { hwLvdBranchEntry 7 }

        hwSetLvdReconnectedVoltage OBJECT-TYPE
            SYNTAX Integer32 (370..580)
            MAX-ACCESS read-write
            STATUS current
            DESCRIPTION
                "Low-voltage power-off recover of a power-off unit can be configured by users. 
                Its value range: 37.0 to 58.0, 
                unit: V, 
                and the value is accurate to one decimal space (.1).  
                If the value is 2147483647(0x7FFFFFFF), it indicates that the value is invalid.
                The default value is 51.5
                NOTE: There is linkage between hwSetLvdVoltage and hwSetLvdReconnectedVoltage"
            ::= { hwLvdBranchEntry 8 }

        hwSetLvdDisconnectedTime OBJECT-TYPE
            SYNTAX Integer32 (0..6000)
            MAX-ACCESS read-write
            STATUS current
            DESCRIPTION
                "Low-voltage power-off disconnected time, It can be configured by users,
                value range defines between 0 to 6000, 
                unit: minutes(min) ，
                and its value is an integer (1). 
                Here, if battery manual test is standard mode, 
                If the value is 2147483647(0x7FFFFFFF), it indicates that the value is invalid.
                NOTE: Only the lvd in time power off mode, this parameter can be configured successfully."
            ::= { hwLvdBranchEntry 9 }

        hwSetLvdDisconnectedCapacity OBJECT-TYPE
            SYNTAX Integer32 (0..990)
            MAX-ACCESS read-write
            STATUS current
            DESCRIPTION
                "Power-off unit control the power off, when Remaining capacity percentage of the battery strings is below the calue. 
                Value range: 0 to 99, 
                unit: %, 
                and the value is accurate to one decimal space (.1). 
                If the value is 2147483647(0x7FFFFFFF), it indicates that the value is invalid.
                NOTE: Only the lvd in capacity power off mode, this parameter can be configured successfully."
            ::= { hwLvdBranchEntry 10 }

        hwLvdBranchOperStatus OBJECT-TYPE
            SYNTAX INTEGER
                {
                normal(1),
                lowVoltOff(2),
                backgroundOff(3),
                localManualOff(4),
                lowTempOff(5),
                highTempOff(6),
                timeOff(7),
                capacityOff(8),
                forceOff(9),
                alarmResume(254),
                unknown(255)
                }
            MAX-ACCESS read-only
            STATUS current
            DESCRIPTION
                "State of the site LVD uint. It is an enumeration type: 
                  If the enumeration value is 1, the site LVD uint is in the normal state;
                  If the enumeration value is 2, the power-off uint disconnect for low voltage;  
                  If the enumeration value is 3, the power-off uint disconnect bakeground;   
                  If the enumeration value is 4, the power-off uint local disconnect manually;  
                  If the enumeration value is 5, the power-off uint disconnect for under temperature; 
                  If the enumeration value is 6, the power-off uint disconnect for over temperature; 
                  If the enumeration value is 7, the ower-off uint disconnect for time;
                If the enumeration value is 8, the power-off uint disconnect for capacity;
                If the enumeration value is 9, the power-off uint disconnect for force;
                  If the enumeration value is 254, the power-off uint alarm resume; 
                  If the enumeration value is 255, it indicates LVD uint operation status unknown. "
            ::= { hwLvdBranchEntry 99 }

        hwLvdBranchRowStatus OBJECT-TYPE
            SYNTAX RowStatus
            MAX-ACCESS read-create
            STATUS current
            DESCRIPTION
                "RowStatus of lvd table."
            ::= { hwLvdBranchEntry 100 }

        hwSiteEnvUnits OBJECT IDENTIFIER ::= { hwSiteMonitorMIBObjects 8 }

        hwEnvUnitsGroup OBJECT IDENTIFIER ::= { hwSiteEnvUnits 1 }

        hwEnvUnitsGroupId OBJECT-TYPE
            SYNTAX Unsigned32
            MAX-ACCESS read-only
            STATUS current
            DESCRIPTION
                "Unit group ID of the site environment. It is the unique ID of the unit group on the site. 
                The first digits indicate the device type. The last three digits indicate the device SN. If the last three digits are 000, it indicates a virtual device. "
            ::= { hwEnvUnitsGroup 1 }

        hwEnvUnitsGroupName OBJECT-TYPE
            SYNTAX OCTET STRING (SIZE (0..63))
            MAX-ACCESS read-write
            STATUS current
            DESCRIPTION
                "Unit group name of the site environment, of the character string type, can be configured by users.
                Otherwise, the configured character can not be any other languages except English."
            ::= { hwEnvUnitsGroup 2 }

        hwCtrlSmokeReset OBJECT-TYPE
            SYNTAX INTEGER
                {
                normal(1),
                reset(2),
                nullOper(255)
                }
            MAX-ACCESS read-write
            STATUS current
            DESCRIPTION
                "Smoke sensor reset. It manually controls clearance of the smoke sensor alarm, and this node is of the enumeration type. 
                If the enumeration value of the node is 1, it indicates that the reset of the smoke sensor is not required. 
                If the enumeration value of the node is 2, it indicates that the background controls the reset of the smoke sensor. 
                If the enumeration value of the node is 255, it indicates that the background controls the unknown of the smoke sensor. "
            ::= { hwEnvUnitsGroup 3 }

        hwEnvTempSensorsTotalQuantity OBJECT-TYPE
            SYNTAX Unsigned32 (0..256)
            MAX-ACCESS read-only
            STATUS current
            DESCRIPTION
                "Quantity of the environment temperature sensors, and its value range: 0 to 256."
            ::= { hwEnvUnitsGroup 6 }

        hwEnvHumiSensorsTotalQuantity OBJECT-TYPE
            SYNTAX Unsigned32 (0..256)
            MAX-ACCESS read-only
            STATUS current
            DESCRIPTION
                "Quantity of the environment humidity sensors, and its value range: 0 to 256."
            ::= { hwEnvUnitsGroup 7 }

        hwSpareDigitalsTotalQuantity OBJECT-TYPE
            SYNTAX Unsigned32 (0..256)
            MAX-ACCESS read-only
            STATUS current
            DESCRIPTION
                "Quantity of the Spare digitals, and its value range: 0 to 256."
            ::= { hwEnvUnitsGroup 8 }

        hwSpareDigitalsOutputQuantity OBJECT-TYPE
            SYNTAX Unsigned32 (0..256)
            MAX-ACCESS read-only
            STATUS current
            DESCRIPTION
                "Quantity of the Spare digitals Output, and its value range: 0 to 256."
            ::= { hwEnvUnitsGroup 9 }

        hwEnvSensor OBJECT IDENTIFIER ::= { hwSiteEnvUnits 2 }

        hwEnvTempSensorTable OBJECT-TYPE
            SYNTAX SEQUENCE OF HwEnvTempSensorEntry
            MAX-ACCESS not-accessible
             STATUS current
             DESCRIPTION
                "Site environment temperature table. 
                Use this table to get environment temperature equipment ID, environment temperature equipment name, and environment temperature, set environment temperature upper limit, environment temperature lower limit, and environment temperature alarm enable. 
                This table's index is hwEnvTempSensorIndex, which qualificated by hwEnvTempSensorsQuantity, clone site environment temperature table."
            ::= { hwEnvSensor 1 }

        hwEnvTempSensorEntry OBJECT-TYPE
                        SYNTAX HwEnvTempSensorEntry
            MAX-ACCESS not-accessible
             STATUS current
             DESCRIPTION
                "Site environment temperature table. 
                Use this table to get environment temperature equipment ID, environment temperature equipment name, and environment temperature, set environment temperature upper limit, environment temperature lower limit, and environment temperature alarm enable. 
                This table's index is hwEnvTempSensorIndex, which qualificated by hwEnvTempSensorsQuantity, clone site environment temperature table."
            INDEX { hwEnvTempSensorIndex }
            ::= { hwEnvTempSensorTable 1 }

        HwEnvTempSensorEntry            ::= SEQUENCE {
                hwEnvTempSensorIndex
                    Integer32,
                hwEnvTempEquipId
                    Unsigned32,
                hwEnvTempEquipName
                    OCTET STRING,
                hwEnvTemperature
                    Integer32,
                hwSetEnvTempUpperLimit
                    Integer32,
                hwSetEnvTempLowerLimit
                    Integer32,
                hwSetEnvTempUltraHighTempThreshold
                    Unsigned32,
                hwEnvTempSensorOperStatus
                    INTEGER
            }

        hwEnvTempSensorIndex OBJECT-TYPE
            SYNTAX Integer32 (1..256)
            MAX-ACCESS read-only
            STATUS current
            DESCRIPTION
                "Table index of the environment temperature sensors.
                Value range: 1 to 256. 
                Lines of the device table are restricted by the quantity of environment temperature sensors (hwEnvTempSensorsTotalQuantity). "
            ::= { hwEnvTempSensorEntry 1 }

        hwEnvTempEquipId OBJECT-TYPE
            SYNTAX Unsigned32 (9001..9255)
            MAX-ACCESS read-only
            STATUS current
            DESCRIPTION
                "Environment temperature sensor ID. Value range: 009'001 to 009'255, in which the first digits indicate the device type and the last three digits indicate the device SN. "
            ::= { hwEnvTempSensorEntry 2 }

        hwEnvTempEquipName OBJECT-TYPE
            SYNTAX OCTET STRING (SIZE (0..63))
            MAX-ACCESS read-only
            STATUS current
            DESCRIPTION
                "Environment temperature sensor name, of the character string type,  is used to specify an environment temperature sensor. 
                Users can configure it. Otherwise, the configured character can not be any other languages except English. "
            ::= { hwEnvTempSensorEntry 3 }

        hwEnvTemperature OBJECT-TYPE
            SYNTAX Integer32 ( -50..100)
            MAX-ACCESS read-only
            STATUS current
            DESCRIPTION
                "Environment temperature. It is an environment parameter collected in real time. 
                Value range: -50 to +100, 
                units: centigrade (degC), 
                and the value is an integer (1).  
                If the value is 2147483647, it indicates that the temperature sensor is not configured."
            ::= { hwEnvTempSensorEntry 4 }

        hwSetEnvTempUpperLimit OBJECT-TYPE
            SYNTAX Integer32 ( 25..80)
            MAX-ACCESS read-write
            STATUS current
            DESCRIPTION
                "Upper threshold of the environment temperature alarm, can be configured by users. 
                Value range: 25 to 80, 
                units: centigrade (degC), 
                and the value is an integer (1). 
                If the value is 2147483647(0x7FFFFFFF), it indicates that the value is invalid.
                NOTE: There is linkage between hwSetEnvTempUpperLimit and hwSetEnvTempLowerLimit, All Sensors are set and get the same limit signal;"
            ::= { hwEnvTempSensorEntry 5 }

        hwSetEnvTempLowerLimit OBJECT-TYPE
            SYNTAX Integer32 ( -20..20)
            MAX-ACCESS read-write
            STATUS current
            DESCRIPTION
                "Lower threshold of the environment temperature alarm, can be configured by users. 
                Value range: -20 to 20, 
                units: centigrade (degC), 
                and the value is an integer (1).  
                If the value is 2147483647(0x7FFFFFFF), it indicates that the value is invalid.
                NOTE: There is linkage between hwSetEnvTempUpperLimit and hwSetEnvTempLowerLimit, All Sensors are set and get the same limit signal;"
            ::= { hwEnvTempSensorEntry 6 }

        hwSetEnvTempUltraHighTempThreshold OBJECT-TYPE
            SYNTAX Unsigned32 ( 25..80)
            MAX-ACCESS read-write
            STATUS current
            DESCRIPTION
                "Threshold of the environment ultra high temperature measurement, can be configured by users.
                Value range: 25 to 80,
                unit: centigrade (degC),
                and the value is an integer (1).
                If the value is 2147483647(0x7FFFFFFF), it indicates that the value is invalid, All Sensors are set and get the same limit signal;
                "
            ::= { hwEnvTempSensorEntry 10 }

        hwEnvTempSensorOperStatus OBJECT-TYPE
            SYNTAX INTEGER
                {
                normal(1),
                tempHigh(2),
                tempLow(3),
                notInslot(4),
                alarmResume(254),
                unknown(255)
                }
            MAX-ACCESS read-only
            STATUS current
            DESCRIPTION
                "State of the site environment temperature sensor. It is an enumeration type: 
                  If the enumeration value is 1, it indicates that the site environment temperature sensor is in the normal state; 
                  If the enumeration value is 2, it indicates that the environment temperature sensor is over temperature; 
                  If the enumeration value is 3, it indicates that the environment temperature sensor is under temperature; 
                  If the enumeration value is 4, it indicates that the environment temperature sensor is not in slot;
                  If the enumeration value is 254, it indicates that environment temperature alarm resume; 
                  If the enumeration value is 255, it indicates environment temperature sensor operation status unknown. "
            ::= { hwEnvTempSensorEntry 99 }

        hwSpareDigitalTable OBJECT-TYPE
            SYNTAX SEQUENCE OF HwSpareDigitalEntry
            MAX-ACCESS not-accessible
             STATUS current
             DESCRIPTION
                "Spare digital table. Use this table to get Spare digital equipment ID , Spare digital equipment name, and current Spare digital alarm tension, ae well as to set Spare digital alarm enable. This table's index is hwSpareDigitalIndex, which qualificated by hwSpareDigitalsTotalQuantity, clone switch input table."
            ::= { hwEnvSensor 3 }

        hwSpareDigitalEntry OBJECT-TYPE
                        SYNTAX HwSpareDigitalEntry
            MAX-ACCESS not-accessible
             STATUS current
             DESCRIPTION
                "Spare digital table. Use this table to get Spare digital equipment ID , Spare digital equipment name, and current Spare digital alarm tension, ae well as to set Spare digital alarm enable. This table's index is hwSpareDigitalIndex, which qualificated by hwSpareDigitalsTotalQuantity, clone switch input table."
            INDEX { hwSpareDigitalIndex }
            ::= { hwSpareDigitalTable 1 }

        HwSpareDigitalEntry            ::= SEQUENCE {
                hwSpareDigitalIndex
                    Integer32,
                hwSpareDigitalEquipId
                    Unsigned32,
                hwSpareDigitalEquipName
                    OCTET STRING,
                hwSpareDigitalAlarmTension
                    INTEGER,
                hwSpareDigitalOperStatus
                    INTEGER
            }

        hwSpareDigitalIndex OBJECT-TYPE
            SYNTAX Integer32 (1..256)
            MAX-ACCESS read-only
            STATUS current
            DESCRIPTION
                "Spare digital table index, which 
                value range: 1 to 256. 
                Lines of the device list are restricted by the quantity of Spare digitals (hwSpareDigitalsTotalQuantity). "
            ::= { hwSpareDigitalEntry 1 }

        hwSpareDigitalEquipId OBJECT-TYPE
            SYNTAX Unsigned32 (11001..11255)
            MAX-ACCESS read-only
            STATUS current
            DESCRIPTION
                "Spare digital device ID. Value range: 011'001 to 011'255, in which the first digits indicate the device type and the last three digits indicate the device SN. "
            ::= { hwSpareDigitalEntry 2 }

        hwSpareDigitalEquipName OBJECT-TYPE
            SYNTAX OCTET STRING (SIZE (0..8))
            MAX-ACCESS read-only
            STATUS current
            DESCRIPTION
                "Spare digital name, of the character string type, is used to specify Spare digitals. Users can configure it. Otherwise, the configured character can not be any other languages except English. "
            ::= { hwSpareDigitalEntry 3 }

        hwSpareDigitalAlarmTension OBJECT-TYPE
            SYNTAX INTEGER
                {
                open(0),
                close(1)
                }
            MAX-ACCESS read-write
            STATUS current
            DESCRIPTION
                "Spare digital alarm state. It is an enumeration value.  
                  If the value of the node is 1, it indicates a low-tension alarm;
                  If the value of the node is 2, it indicates a high-tension alarm. "
            ::= { hwSpareDigitalEntry 4 }

        hwSpareDigitalOperStatus OBJECT-TYPE
            SYNTAX INTEGER
                {
                normal(1),
                alarm(2),
                alarmResume(254),
                unknown(255)
                }
            MAX-ACCESS read-only
            STATUS current
            DESCRIPTION
                "State of the site Spare digital. It is an enumeration type: 
                  If the enumeration value is 1, it indicates that the Spare digital operation state is normal; 
                  If the enumeration value is 2, it indicates that a alarm occurs on the Spare digital;  
                  If the enumeration value is 254, it indicates that spare digital alarm resume;  
                  If the enumeration value is 255, it indicates Spare digital operation status unknown."
            ::= { hwSpareDigitalEntry 99 }

        hwSpareDigitalOutputTable OBJECT-TYPE
            SYNTAX SEQUENCE OF HwSpareDigitalOutputEntry
            MAX-ACCESS not-accessible
             STATUS current
             DESCRIPTION
                "Spare digital table. Use this table to get Spare digital equipment ID , Spare digital equipment name, and current Spare digital alarm tension, ae well as to set Spare digital alarm enable. This table's index is hwSpareDigitalIndex, which qualificated by hwSpareDigitalsTotalQuantity, clone switch input table."
            ::= { hwEnvSensor 4 }

        hwSpareDigitalOutputEntry OBJECT-TYPE
                        SYNTAX HwSpareDigitalOutputEntry
            MAX-ACCESS not-accessible
             STATUS current
             DESCRIPTION
                "Spare digital table. Use this table to get Spare digital equipment ID , Spare digital equipment name, and current Spare digital alarm tension, ae well as to set Spare digital alarm enable. This table's index is hwSpareDigitalIndex, which qualificated by hwSpareDigitalsTotalQuantity, clone switch input table."
            INDEX { hwSpareDigitalOutputIndex }
            ::= { hwSpareDigitalOutputTable 1 }

        HwSpareDigitalOutputEntry            ::= SEQUENCE {
                hwSpareDigitalOutputIndex
                    Integer32,
                hwSpareDigitalOutputEquipId
                    Unsigned32,
                hwSpareDigitalOutputEquipName
                    OCTET STRING,
                hwSetSpareDigitalOutputAlarmCondition
                    INTEGER,
                hwSpareDigitalOutputOperStatus
                    INTEGER
            }

        hwSpareDigitalOutputIndex OBJECT-TYPE
            SYNTAX Integer32 (1..256)
            MAX-ACCESS read-only
            STATUS current
            DESCRIPTION
                "Spare digital table index, which 
                value range: 1 to 256. 
                Lines of the device list are restricted by the quantity of Spare digitals (hwSpareDigitalsTotalQuantity). "
            ::= { hwSpareDigitalOutputEntry 1 }

        hwSpareDigitalOutputEquipId OBJECT-TYPE
            SYNTAX Unsigned32 (12001..12255)
            MAX-ACCESS read-only
            STATUS current
            DESCRIPTION
                "Spare digital device ID. Value range: 012'001 to 012'255, in which the first digits indicate the device type and the last three digits indicate the device SN. "
            ::= { hwSpareDigitalOutputEntry 2 }

        hwSpareDigitalOutputEquipName OBJECT-TYPE
            SYNTAX OCTET STRING (SIZE (0..63))
            MAX-ACCESS read-only
            STATUS current
            DESCRIPTION
                "Spare digital name, of the character string type, is used to specify Spare digitals. Users can configure it. Otherwise, the configured character can not be any other languages except English. "
            ::= { hwSpareDigitalOutputEntry 3 }

        hwSetSpareDigitalOutputAlarmCondition OBJECT-TYPE
            SYNTAX INTEGER
                {
                open(1),
                close(2)
                }
            MAX-ACCESS read-write
            STATUS current
            DESCRIPTION
                "Spare digital alarm state. It is an enumeration value.  
                  If the value of the node is 1, it indicates a low-tension alarm;
                  If the value of the node is 2, it indicates a high-tension alarm. "
            ::= { hwSpareDigitalOutputEntry 4 }

        hwSpareDigitalOutputOperStatus OBJECT-TYPE
            SYNTAX INTEGER
                {
                open(1),
                close(2),
                alarmResume(254),
                unknown(255)
                }
            MAX-ACCESS read-only
            STATUS current
            DESCRIPTION
                "State of the site Spare digital. It is an enumeration type: 
                  If the enumeration value is 1, it indicates that the Spare digital operation state is normal; 
                  If the enumeration value is 2, it indicates that a alarm occurs on the Spare digital;  
                  If the enumeration value is 254, it indicates that spare digital alarm resume;  
                  If the enumeration value is 255, it indicates Spare digital operation status unknown."
            ::= { hwSpareDigitalOutputEntry 99 }

        hwSiteCoolingDevices OBJECT IDENTIFIER ::= { hwSiteMonitorMIBObjects 10 }

        hwCoolingDevicesEquip OBJECT IDENTIFIER ::= { hwSiteCoolingDevices 2 }

        hwDcAirConditionTable OBJECT-TYPE
            SYNTAX SEQUENCE OF HwDcAirConditionEntry
            MAX-ACCESS not-accessible
             STATUS current
             DESCRIPTION
                ""
            ::= { hwCoolingDevicesEquip 2 }

        hwDcAirConditionEntry OBJECT-TYPE
                        SYNTAX HwDcAirConditionEntry
            MAX-ACCESS not-accessible
             STATUS current
             DESCRIPTION
                ""
            INDEX { hwDcAirIndex }
            ::= { hwDcAirConditionTable 1 }

        HwDcAirConditionEntry            ::= SEQUENCE {
                hwDcAirIndex
                    Unsigned32,
                hwDcAirEquipId
                    Unsigned32,
                hwDcAirEquipName
                    OCTET STRING,
                hwDcAirCtrlMode
                    INTEGER,
                hwDcAirCtrlOnOff
                    INTEGER,
                hwDcAirRunStatus
                    INTEGER,
                hwDcAirCompressorRunStatus
                    INTEGER,
                hwDcAirInnrFanSpeed
                    Integer32,
                hwDcAirOuterFanSpeed
                    Integer32,
                hwDcAirCompressorRunTime
                    Integer32,
                hwDcAirRunTime
                    Integer32,
                hwDcAirEnterChannelTemp
                    Integer32,
                hwDcAirOperStatus
                    INTEGER,
                hwDcAirRowStatus
                    RowStatus
            }

        hwDcAirIndex OBJECT-TYPE
            SYNTAX Unsigned32 (1..256)
            MAX-ACCESS read-only
            STATUS current
            DESCRIPTION
                "Dc aircondition table index,which value range: 1 to 256.Lines of the device list are restricted by the quantity of Fan."
            ::= { hwDcAirConditionEntry 1 }

        hwDcAirEquipId OBJECT-TYPE
            SYNTAX Unsigned32 (21001..21255)
            MAX-ACCESS read-only
            STATUS current
            DESCRIPTION
                "Dc aircondition device ID. Value range: 021'001 to 021'255, in which the first digits indicate the device type and the last three digits indicate the device SN. "
            ::= { hwDcAirConditionEntry 2 }

        hwDcAirEquipName OBJECT-TYPE
            SYNTAX OCTET STRING (SIZE (0..63))
            MAX-ACCESS read-only
            STATUS current
            DESCRIPTION
                "Dc aircondition name, of the character string type, is used to specify Fans. Users can configure it.
                Otherwise, the configured character can not be any other languages except English. "
            ::= { hwDcAirConditionEntry 3 }

        hwDcAirCtrlMode OBJECT-TYPE
            SYNTAX INTEGER
                {
                autoControl(1),
                manualControl(2),
                unknown(255)
                }
            MAX-ACCESS read-write
            STATUS current
            DESCRIPTION
                "State of the Dc aircondition ctrl mode. It is an enumeration type: 
                If the enumeration value is 1, it indicates that the Dc aircondition is in autoControl state;
                If the enumeration value is 2, it indicates that the Dc aircondition is in manualControl state;
                If the enumeration value is 255, it indicates that the Dc aircondition is in unknown state;"
            ::= { hwDcAirConditionEntry 4 }

        hwDcAirCtrlOnOff OBJECT-TYPE
            SYNTAX INTEGER
                {
                on(1),
                off(2)
                }
            MAX-ACCESS read-write
            STATUS current
            DESCRIPTION
                "State of the Dc aircondition control on or off. It is an enumeration type: 
                If the enumeration value is 1, it indicates that the Dc aircondition is in on state;
                If the enumeration value is 2, it indicates that the Dc aircondition is in off state;"
            ::= { hwDcAirConditionEntry 5 }

        hwDcAirRunStatus OBJECT-TYPE
            SYNTAX INTEGER
                {
                standby(1),
                run(2),
                fault(3),
                unknown(255)
                }
            MAX-ACCESS read-only
            STATUS current
            DESCRIPTION
                "State of the Dc aircondition run status. It is an enumeration type: 
                If the enumeration value is 1, it indicates that the Dc aircondition is in standby state;
                If the enumeration value is 2, it indicates that the Dc aircondition is in run state;
                If the enumeration value is 3, it indicates that the Dc aircondition is in fault state;
                If the enumeration value is 255, it indicates that the Dc aircondition is other state."
            ::= { hwDcAirConditionEntry 6 }

        hwDcAirCompressorRunStatus OBJECT-TYPE
            SYNTAX INTEGER
                {
                standby(1),
                run(2),
                fault(3),
                unknown(255)
                }
            MAX-ACCESS read-only
            STATUS current
            DESCRIPTION
                "State of the Dc air compressor run status. It is an enumeration type: 
                If the enumeration value is 1, it indicates that the Dc aircondition is in standby state;
                If the enumeration value is 2, it indicates that the Dc aircondition is in run state;
                If the enumeration value is 3, it indicates that the Dc aircondition is in fault state;
                If the enumeration value is 255, it indicates that the Dc aircondition is unknown state."
            ::= { hwDcAirConditionEntry 7 }

        hwDcAirInnrFanSpeed OBJECT-TYPE
            SYNTAX Integer32 (0..60000)
            MAX-ACCESS read-only
            STATUS current
            DESCRIPTION
                "Dc aircondition innr speed, 
                Value range: 0 to 60000.
                Unit: rpm,
                and the value is an integer (1).
                If the value is 2147483647(0x7FFFFFFF), it indicates that the value is invalid."
            ::= { hwDcAirConditionEntry 8 }

        hwDcAirOuterFanSpeed OBJECT-TYPE
            SYNTAX Integer32 (0..60000)
            MAX-ACCESS read-only
            STATUS current
            DESCRIPTION
                "Dc aircondition outer speed, 
                Value range: 0.0 to 60000.0.
                Unit: rpm,
                and the value is an integer (1).
                If the value is 2147483647(0x7FFFFFFF), it indicates that the value is invalid."
            ::= { hwDcAirConditionEntry 9 }

        hwDcAirCompressorRunTime OBJECT-TYPE
            SYNTAX Integer32 (0..175200)
            MAX-ACCESS read-only
            STATUS current
            DESCRIPTION
                "Dc aircondition compressor run time, 
                Value range: 0 to 175200.
                Unit: h,
                the value is an integer (1). 
                If the value is 2147483647(0x7FFFFFFF), it indicates that the value is invalid."
            ::= { hwDcAirConditionEntry 10 }

        hwDcAirRunTime OBJECT-TYPE
            SYNTAX Integer32 (0..175200)
            MAX-ACCESS read-only
            STATUS current
            DESCRIPTION
                "Dc aircondition run time, 
                Value range: 0 to 175200.
                Unit: H,
                the value is an integer (1). 
                If the value is 2147483647(0x7FFFFFFF), it indicates that the value is invalid."
            ::= { hwDcAirConditionEntry 11 }

        hwDcAirEnterChannelTemp OBJECT-TYPE
            SYNTAX Integer32 ( -500..1000)
            MAX-ACCESS read-only
            STATUS current
            DESCRIPTION
                "Dc aircondition enter channel temperature, 
                Value range:-500.0 to 1000.0.
                Unit: degC.
                and the value is an integer (1).   
                If the value is 2147483647(0x7FFFFFFF), it indicates that the value is invalid."
            ::= { hwDcAirConditionEntry 13 }

        hwDcAirOperStatus OBJECT-TYPE
            SYNTAX INTEGER
                {
                standby(1),
                run(2),
                fault(3),
                alarmResume(254),
                unknown(255)
                }
            MAX-ACCESS read-only
            STATUS current
            DESCRIPTION
                "State of the dc aircondition. It is an enumeration type: 
                If the enumeration value is 1, it indicates that the Inverter is in the standby state;
                If the enumeration value is 2, it indicates that the Inverter is in the run state;  
                If the enumeration value is 3, it indicates that the Inverter is in the fault state;
                If the enumeration value is 254, it indicates that the Inverter is in the resume state;     
                If the enumeration value is 255, it indicates Inverter operation status unknown. "
            ::= { hwDcAirConditionEntry 99 }

        hwDcAirRowStatus OBJECT-TYPE
            SYNTAX RowStatus
            MAX-ACCESS read-create
            STATUS current
            DESCRIPTION
                "RowStatus fo dc aircondition table."
            ::= { hwDcAirConditionEntry 100 }

        hwSiteAcAmmeters OBJECT IDENTIFIER ::= { hwSiteMonitorMIBObjects 11 }

        hwSiteAcAmmeterEquip OBJECT IDENTIFIER ::= { hwSiteAcAmmeters 2 }

        hwSiteAcAmmeterTable OBJECT-TYPE
            SYNTAX SEQUENCE OF HwSiteAcAmmeterEntry
            MAX-ACCESS not-accessible
             STATUS current
             DESCRIPTION
                "/"
            ::= { hwSiteAcAmmeterEquip 1 }

        hwSiteAcAmmeterEntry OBJECT-TYPE
                        SYNTAX HwSiteAcAmmeterEntry
            MAX-ACCESS not-accessible
             STATUS current
             DESCRIPTION
                "/"
            INDEX { hwAcAmmeterIndex }
            ::= { hwSiteAcAmmeterTable 1 }

        HwSiteAcAmmeterEntry            ::= SEQUENCE {
                hwAcAmmeterIndex
                    Unsigned32,
                hwAcAmmeterEquipId
                    Unsigned32,
                hwAcAmmeterEquipName
                    OCTET STRING,
                hwAcAmmeterFrequency
                    Unsigned32,
                hwAcAmmeterPhaseL1Voltage
                    Unsigned32,
                hwAcAmmeterPhaseL2Voltage
                    Unsigned32,
                hwAcAmmeterPhaseL3Voltage
                    Unsigned32,
                hwAcAmmeterSetChannelNum
                    Unsigned32,
                hwAcAmmeterClear
                    INTEGER,
                hwAcAmmeterType
                    Unsigned32,
                hwAcAmmeterVersion
                    OCTET STRING,
                hwAcAmmeterPhaseL1CurrentCH1
                    Unsigned32,
                hwAcAmmeterPhaseL2CurrentCH1
                    Unsigned32,
                hwAcAmmeterPhaseL3CurrentCH1
                    Unsigned32,
                hwAcAmmeterTotalActivePowerCH1
                    Integer32,
                hwAcAmmeterTotalPowerFactorCH1
                    Integer32,
                hwAcAmmeterTotalActiveEngryAccCH1
                    Unsigned32,
                hwAcAmmeterPhaseL1CurrentCH2
                    Unsigned32,
                hwAcAmmeterPhaseL2CurrentCH2
                    Unsigned32,
                hwAcAmmeterPhaseL3CurrentCH2
                    Unsigned32,
                hwAcAmmeterTotalActivePowerCH2
                    Integer32,
                hwAcAmmeterTotalPowerFactorCH2
                    Integer32,
                hwAcAmmeterTotalActiveEngryAccCH2
                    Unsigned32,
                hwAcAmmeterPhaseL1CurrentCH3
                    Unsigned32,
                hwAcAmmeterPhaseL2CurrentCH3
                    Unsigned32,
                hwAcAmmeterPhaseL3CurrentCH3
                    Unsigned32,
                hwAcAmmeterTotalActivePowerCH3
                    Integer32,
                hwAcAmmeterTotalPowerFactorCH3
                    Integer32,
                hwAcAmmeterTotalActiveEngryAccCH3
                    Unsigned32,
                hwAcAmmeterPhaseL1CurrentCH4
                    Unsigned32,
                hwAcAmmeterPhaseL2CurrentCH4
                    Unsigned32,
                hwAcAmmeterPhaseL3CurrentCH4
                    Unsigned32,
                hwAcAmmeterTotalActivePowerCH4
                    Integer32,
                hwAcAmmeterTotalPowerFactorCH4
                    Integer32,
                hwAcAmmeterTotalActiveEngryAccCH4
                    Unsigned32,
                hwAcAmmeterOperStatus
                    INTEGER,
                hwAcAmmeterRowStatus
                    RowStatus
            }

        hwAcAmmeterIndex OBJECT-TYPE
            SYNTAX Unsigned32 (4096..20479)
            MAX-ACCESS read-only
            STATUS current
            DESCRIPTION
                "Ac Ammeter table index,which value range:4096 to 20479. Lines of the device list are restricted by the quantity of AcAmmeter"
            ::= { hwSiteAcAmmeterEntry 1 }

        hwAcAmmeterEquipId OBJECT-TYPE
            SYNTAX Unsigned32 (22001..22255)
            MAX-ACCESS read-only
            STATUS current
            DESCRIPTION
                "Ac Ammeter device ID. Value range: 022'001 to 022'255, in which the first digits indicate the device type and the last three digits indicate the device SN."
            ::= { hwSiteAcAmmeterEntry 2 }

        hwAcAmmeterEquipName OBJECT-TYPE
            SYNTAX OCTET STRING (SIZE (0..63))
            MAX-ACCESS read-only
            STATUS current
            DESCRIPTION
                "Ac Ammeter name, of the character string type, is used to specify Fans. Users can configure it.
                Otherwise, the configured character can not be any other languages except English.
                "
            ::= { hwSiteAcAmmeterEntry 3 }

        hwAcAmmeterFrequency OBJECT-TYPE
            SYNTAX Unsigned32 (0..100000)
            MAX-ACCESS read-only
            STATUS current
            DESCRIPTION
                "Ac Ammeter frequency, 
                Value range: 0.00 to 1000.00.
                Unit: Hz.
                and the value is accurate to two decimal space (.01). 
                If the value is 2147483647(0x7FFFFFFF), it indicates that the value is invalid."
            ::= { hwSiteAcAmmeterEntry 4 }

        hwAcAmmeterPhaseL1Voltage OBJECT-TYPE
            SYNTAX Unsigned32 (0..200000)
            MAX-ACCESS read-only
            STATUS current
            DESCRIPTION
                "Ac Ammeter phase a voltage, 
                Value range: 0.00 to 2000.00.
                Unit: V.
                and the value is accurate to two decimal space (.01). 
                If the value is 2147483647(0x7FFFFFFF), it indicates that the value is invalid."
            ::= { hwSiteAcAmmeterEntry 5 }

        hwAcAmmeterPhaseL2Voltage OBJECT-TYPE
            SYNTAX Unsigned32 (0..200000)
            MAX-ACCESS read-only
            STATUS current
            DESCRIPTION
                "Ac Ammeter phase b voltage, 
                Value range: 0.00 to 2000.0.
                Unit: V.
                and the value is accurate to two decimal space (.01).
                If the value is 2147483647(0x7FFFFFFF), it indicates that the value is invalid."
            ::= { hwSiteAcAmmeterEntry 6 }

        hwAcAmmeterPhaseL3Voltage OBJECT-TYPE
            SYNTAX Unsigned32 (0..200000)
            MAX-ACCESS read-only
            STATUS current
            DESCRIPTION
                "Ac Ammeter phase c voltage, 
                Value range: 0.00 to 2000.0.
                Unit: V.
                and the value is accurate to two decimal space (.01). 
                If the value is 2147483647(0x7FFFFFFF), it indicates that the value is invalid."
            ::= { hwSiteAcAmmeterEntry 7 }

        hwAcAmmeterSetChannelNum OBJECT-TYPE
            SYNTAX Unsigned32 (1..4)
            MAX-ACCESS read-write
            STATUS current
            DESCRIPTION
                "Ac Ammeter set channel number, 
                Value range: 1 to 4. 
                Unit: NA.
                and the value is an integer (1).
                If the value is 2147483647(0x7FFFFFFF), it indicates that the value is invalid."
            ::= { hwSiteAcAmmeterEntry 8 }

        hwAcAmmeterClear OBJECT-TYPE
            SYNTAX INTEGER
                {
                clear(1)
                }
            MAX-ACCESS read-write
            STATUS current
            DESCRIPTION
                "Ac Ammeter clear communication failure . It is an enumeration type: 
                If the enumeration value is 1, it indicates that the ac ammeter clear communication failure alarm;"
            ::= { hwSiteAcAmmeterEntry 9 }

        hwAcAmmeterType OBJECT-TYPE
            SYNTAX Unsigned32 (0..65535)
            MAX-ACCESS read-only
            STATUS current
            DESCRIPTION
                "Ac Ammeter type, Value range: 0 to 65535. And the value is an integer(1)."
            ::= { hwSiteAcAmmeterEntry 10 }

        hwAcAmmeterVersion OBJECT-TYPE
            SYNTAX OCTET STRING (SIZE (0..56))
            MAX-ACCESS read-only
            STATUS current
            DESCRIPTION
                "Ac Ammeter version, of the character string type, is used to specify Ac Ammeter. Users can not configure it."
            ::= { hwSiteAcAmmeterEntry 11 }

        hwAcAmmeterPhaseL1CurrentCH1 OBJECT-TYPE
            SYNTAX Unsigned32 (0..100000)
            MAX-ACCESS read-only
            STATUS current
            DESCRIPTION
                "Ac Ammeter phase a current of channel 1, 
                Value range: 0.00 to 1000.0.
                Unit: A.
                and the value is accurate to two decimal space (.01). 
                If the value is 2147483647(0x7FFFFFFF), it indicates that the value is invalid."
            ::= { hwSiteAcAmmeterEntry 12 }

        hwAcAmmeterPhaseL2CurrentCH1 OBJECT-TYPE
            SYNTAX Unsigned32 (0..100000)
            MAX-ACCESS read-only
            STATUS current
            DESCRIPTION
                "Ac Ammeter phase b current of channel 1, 
                Value range: 0.00 to 1000.0.
                Unit: A.
                and the value is accurate to two decimal space (.01). 
                If the value is 2147483647(0x7FFFFFFF), it indicates that the value is invalid."
            ::= { hwSiteAcAmmeterEntry 13 }

        hwAcAmmeterPhaseL3CurrentCH1 OBJECT-TYPE
            SYNTAX Unsigned32 (0..100000)
            MAX-ACCESS read-only
            STATUS current
            DESCRIPTION
                "Ac Ammeter phase c current of channel 1, 
                Value range: 0.00 to 1000.0.
                Unit: A.
                and the value is accurate to two decimal space (.01).
                If the value is 2147483647(0x7FFFFFFF), it indicates that the value is invalid."
            ::= { hwSiteAcAmmeterEntry 14 }

        hwAcAmmeterTotalActivePowerCH1 OBJECT-TYPE
            SYNTAX Integer32 (-100000000..100000000)
            MAX-ACCESS read-only
            STATUS current
            DESCRIPTION
                "Ac Ammeter phase c current of channel 1, 
                Value range: -1000000.00 to 1000000.00.
                Unit: kW.
                and the value is accurate to two decimal space (.01). 
                If the value is 2147483647(0x7FFFFFFF), it indicates that the value is invalid."
            ::= { hwSiteAcAmmeterEntry 15 }

        hwAcAmmeterTotalPowerFactorCH1 OBJECT-TYPE
            SYNTAX Integer32 (-1000..1000)
            MAX-ACCESS read-only
            STATUS current
            DESCRIPTION
                "Ac Ammeter total power factor of channel 1, 
                Value range: -10.00 to 10.00.
                and the value is accurate to two decimal space (.01). 
                If the value is 2147483647(0x7FFFFFFF), it indicates that the value is invalid."
            ::= { hwSiteAcAmmeterEntry 16 }

        hwAcAmmeterTotalActiveEngryAccCH1 OBJECT-TYPE
            SYNTAX Unsigned32 (0..10000000000000)
            MAX-ACCESS read-only
            STATUS current
            DESCRIPTION
                "Ac Ammeter total active engry acc of channel 1, 
                Value range: 0.00 to 1000000000.00.
                Unit: kWh.
                and the value is accurate to two decimal space (.01). 
                If the value is 2147483647(0x7FFFFFFF), it indicates that the value is invalid."
            ::= { hwSiteAcAmmeterEntry 17 }

        hwAcAmmeterPhaseL1CurrentCH2 OBJECT-TYPE
            SYNTAX Unsigned32 (0..100000)
            MAX-ACCESS read-only
            STATUS current
            DESCRIPTION
                "Ac Ammeter phase a current of channel 2, 
                Value range: 0.00 to 1000.00.
                Unit: A.
                and the value is accurate to two decimal space (.01).
                If the value is 2147483647(0x7FFFFFFF), it indicates that the value is invalid."
            ::= { hwSiteAcAmmeterEntry 18 }

        hwAcAmmeterPhaseL2CurrentCH2 OBJECT-TYPE
            SYNTAX Unsigned32 (0..100000)
            MAX-ACCESS read-only
            STATUS current
            DESCRIPTION
                "Ac Ammeter phase b current of channel 2, 
                Value range: 0.00 to 1000.00.
                Unit: A.
                and the value is accurate to two decimal space (.01).
                If the value is 2147483647(0x7FFFFFFF), it indicates that the value is invalid."
            ::= { hwSiteAcAmmeterEntry 19 }

        hwAcAmmeterPhaseL3CurrentCH2 OBJECT-TYPE
            SYNTAX Unsigned32 (0..100000)
            MAX-ACCESS read-only
            STATUS current
            DESCRIPTION
                "Ac Ammeter phase c current of channel 2, 
                Value range: 0.00 to 1000.00.
                Unit: A.
                and the value is accurate to two decimal space (.01). 
                If the value is 2147483647(0x7FFFFFFF), it indicates that the value is invalid."
            ::= { hwSiteAcAmmeterEntry 20 }

        hwAcAmmeterTotalActivePowerCH2 OBJECT-TYPE
            SYNTAX Integer32 (-100000000..100000000)
            MAX-ACCESS read-only
            STATUS current
            DESCRIPTION
                "Ac Ammeter phase c current of channel 2, 
                Value range: -1000000.00 to 1000000.00.
                Unit: kW.
                and the value is accurate to two decimal space (.01). 
                If the value is 2147483647(0x7FFFFFFF), it indicates that the value is invalid."
            ::= { hwSiteAcAmmeterEntry 21 }

        hwAcAmmeterTotalPowerFactorCH2 OBJECT-TYPE
            SYNTAX Integer32 (-1000..1000)
            MAX-ACCESS read-only
            STATUS current
            DESCRIPTION
                "Ac Ammeter total power factor of channel 2, 
                Value range: -10.00 to 10.00.
                and the value is accurate to two decimal space (.01). 
                If the value is 2147483647(0x7FFFFFFF), it indicates that the value is invalid."
            ::= { hwSiteAcAmmeterEntry 22 }

        hwAcAmmeterTotalActiveEngryAccCH2 OBJECT-TYPE
            SYNTAX Unsigned32 (0..100000000000)
            MAX-ACCESS read-only
            STATUS current
            DESCRIPTION
                "Ac Ammeter total active engry acc of channel 2, 
                Value range: 0.00 to 1000000000.00.
                Unit: A.
                and the value is accurate to two decimal space (.01). 
                If the value is 2147483647(0x7FFFFFFF), it indicates that the value is invalid."
            ::= { hwSiteAcAmmeterEntry 23 }

        hwAcAmmeterPhaseL1CurrentCH3 OBJECT-TYPE
            SYNTAX Unsigned32 (0..100000)
            MAX-ACCESS read-only
            STATUS current
            DESCRIPTION
                "Ac Ammeter phase a current of channel 3, 
                Value range: 0.00 to 1000.00.
                Unit: A.
                and the value is accurate to two decimal space (.01). 
                If the value is 2147483647(0x7FFFFFFF), it indicates that the value is invalid."
            ::= { hwSiteAcAmmeterEntry 24 }

        hwAcAmmeterPhaseL2CurrentCH3 OBJECT-TYPE
            SYNTAX Unsigned32 (0..100000)
            MAX-ACCESS read-only
            STATUS current
            DESCRIPTION
                "Ac Ammeter phase b current of channel 3, 
                Value range: 0.00 to 1000.00.
                Unit: A.
                and the value is accurate to two decimal space (.01). 
                If the value is 2147483647(0x7FFFFFFF), it indicates that the value is invalid."
            ::= { hwSiteAcAmmeterEntry 25 }

        hwAcAmmeterPhaseL3CurrentCH3 OBJECT-TYPE
            SYNTAX Unsigned32 (0..100000)
            MAX-ACCESS read-only
            STATUS current
            DESCRIPTION
                "Ac Ammeter phase c current of channel 3, 
                Value range: 0.00 to 1000.00.
                Unit: A.
                and the value is accurate to two decimal space (.01). 
                If the value is 2147483647(0x7FFFFFFF), it indicates that the value is invalid."
            ::= { hwSiteAcAmmeterEntry 26 }

        hwAcAmmeterTotalActivePowerCH3 OBJECT-TYPE
            SYNTAX Integer32 (-100000000..100000000)
            MAX-ACCESS read-only
            STATUS current
            DESCRIPTION
                "Ac Ammeter phase c current of channel 3, 
                Value range: -1000000.00 to 1000000.00.
                Unit: kW.
                and the value is accurate to two decimal space (.01). 
                If the value is 2147483647(0x7FFFFFFF), it indicates that the value is invalid."
            ::= { hwSiteAcAmmeterEntry 27 }

        hwAcAmmeterTotalPowerFactorCH3 OBJECT-TYPE
            SYNTAX Integer32 (-1000..1000)
            MAX-ACCESS read-only
            STATUS current
            DESCRIPTION
                "Ac Ammeter total power factor of channel 3, 
                Value range: -10.00 to 10.00.
                and the value is accurate to two decimal space (.01).
                If the value is 2147483647(0x7FFFFFFF), it indicates that the value is invalid."
            ::= { hwSiteAcAmmeterEntry 28 }

        hwAcAmmeterTotalActiveEngryAccCH3 OBJECT-TYPE
            SYNTAX Unsigned32 (0..100000000000)
            MAX-ACCESS read-only
            STATUS current
            DESCRIPTION
                "Ac Ammeter total active engry acc of channel 3, 
                Value range: 0.00 to 1000000000.00.
                Unit: kWh.
                and the value is accurate to two decimal space (.01). 
                If the value is 2147483647(0x7FFFFFFF), it indicates that the value is invalid."
            ::= { hwSiteAcAmmeterEntry 29 }

        hwAcAmmeterPhaseL1CurrentCH4 OBJECT-TYPE
            SYNTAX Unsigned32 (0..100000)
            MAX-ACCESS read-only
            STATUS current
            DESCRIPTION
                "Ac Ammeter phase a current of channel 4, 
                Value range: 0 to 1000.
                Unit: A.
                and the value is accurate to two decimal space (.01). 
                If the value is 2147483647(0x7FFFFFFF), it indicates that the value is invalid."
            ::= { hwSiteAcAmmeterEntry 30 }

        hwAcAmmeterPhaseL2CurrentCH4 OBJECT-TYPE
            SYNTAX Unsigned32 (0..100000)
            MAX-ACCESS read-only
            STATUS current
            DESCRIPTION
                "Ac Ammeter phase b current of channel 4, 
                Value range: 0 to 1000.
                Unit: A.
                and the value is accurate to two decimal space (.01). 
                If the value is 2147483647(0x7FFFFFFF), it indicates that the value is invalid."
            ::= { hwSiteAcAmmeterEntry 31 }

        hwAcAmmeterPhaseL3CurrentCH4 OBJECT-TYPE
            SYNTAX Unsigned32 (0..100000)
            MAX-ACCESS read-only
            STATUS current
            DESCRIPTION
                "Ac Ammeter phase c current of channel 4, 
                Value range: 0 to 1000.
                Unit: A.
                and the value is accurate to two decimal space (.01). 
                If the value is 2147483647(0x7FFFFFFF), it indicates that the value is invalid."
            ::= { hwSiteAcAmmeterEntry 32 }

        hwAcAmmeterTotalActivePowerCH4 OBJECT-TYPE
            SYNTAX Integer32 (-100000000..100000000)
            MAX-ACCESS read-only
            STATUS current
            DESCRIPTION
                "Ac Ammeter phase c current of channel 4, 
                Value range: -1000000 to 1000000.
                Unit: kW.
                and the value is accurate to two decimal space (.01). 
                If the value is 2147483647(0x7FFFFFFF), it indicates that the value is invalid."
            ::= { hwSiteAcAmmeterEntry 33 }

        hwAcAmmeterTotalPowerFactorCH4 OBJECT-TYPE
            SYNTAX Integer32 (-1000..1000)
            MAX-ACCESS read-only
            STATUS current
            DESCRIPTION
                "Ac Ammeter total power factor of channel 4, 
                Value range: -10.00 to 10.00.
                and the value is accurate to two decimal space (.01).
                If the value is 2147483647(0x7FFFFFFF), it indicates that the value is invalid."
            ::= { hwSiteAcAmmeterEntry 34 }

        hwAcAmmeterTotalActiveEngryAccCH4 OBJECT-TYPE
            SYNTAX Unsigned32 (0..100000000000)
            MAX-ACCESS read-only
            STATUS current
            DESCRIPTION
                "Ac Ammeter total active engry acc of channel 4, 
                Value range: 0 to 1000000000.
                Unit: kWh.
                and the value is accurate to two decimal space (.01). 
                If the value is 2147483647(0x7FFFFFFF), it indicates that the value is invalid."
            ::= { hwSiteAcAmmeterEntry 35 }

        hwAcAmmeterOperStatus OBJECT-TYPE
            SYNTAX INTEGER
                {
                normal(1),
                fault(2),
                unknown(255)
                }
            MAX-ACCESS read-only
            STATUS current
            DESCRIPTION
                "State of the Ac Ammeter. It is an enumeration type: 
                If the enumeration value is 1, it indicates that the Ac Ammeter is in the normal state;
                If the enumeration value is 2, it indicates that the Ac Ammeter is in the fault state;  
                If the enumeration value is 255, it indicates that the Ac Ammeter is in the unknown state;  "
            ::= { hwSiteAcAmmeterEntry 99 }

        hwAcAmmeterRowStatus OBJECT-TYPE
            SYNTAX RowStatus
            MAX-ACCESS read-create
            STATUS current
            DESCRIPTION
                "RowStatus fo Ac Ammeter table."
            ::= { hwSiteAcAmmeterEntry 100 }

        hwSiteSSU OBJECT IDENTIFIER ::= { hwSiteMonitorMIBObjects 13 }

        hwSSUGroup OBJECT IDENTIFIER ::= { hwSiteSSU 1 }

        hwSSUGroupId OBJECT-TYPE
            SYNTAX Unsigned32
            MAX-ACCESS read-only
            STATUS current
            DESCRIPTION
                "Device group ID of the SSU module. It is the unique ID of the SSU module group, and its default value: 024,000. 
                The first digits indicate the device type and the last three digits indicate the device SN. If the last three digits are 000, it indicates a virtual device. "
            ::= { hwSSUGroup 1 }

        hwSSUGroupName OBJECT-TYPE
            SYNTAX OCTET STRING (SIZE (0..56))
            MAX-ACCESS read-only
            STATUS current
            DESCRIPTION
                "Name of the SSU module group, character string type, is used to specify the SSU module group. 
                Otherwise, the configured character can not be any other languages except English."
            ::= { hwSSUGroup 2 }

        hwSSUTotalCurrent OBJECT-TYPE
            SYNTAX Unsigned32 (0..10000)
            MAX-ACCESS read-only
            STATUS current
            DESCRIPTION
                "The total output current of SSU. 
                Value range: 0 to 1000, 
                units: A, 
                and the value is one decimal space (.1)."
            ::= { hwSSUGroup 3 }

        hwSSUTotalOutputPower OBJECT-TYPE
            SYNTAX Unsigned32 (0..100000000)
            MAX-ACCESS read-only
            STATUS current
            DESCRIPTION
                "The total output current of SSU. 
                Value range: 0 to 10000000, 
                units: kWh, 
                and the value is one decimal space (.1)."
            ::= { hwSSUGroup 4 }

        hwSSU OBJECT IDENTIFIER ::= { hwSiteSSU 2 }

        hwSSUTable OBJECT-TYPE
            SYNTAX SEQUENCE OF HwSSUEntry
            MAX-ACCESS not-accessible
             STATUS current
             DESCRIPTION
                "/"
            ::= { hwSSU 1 }

        hwSSUEntry OBJECT-TYPE
                        SYNTAX HwSSUEntry
            MAX-ACCESS not-accessible
             STATUS current
             DESCRIPTION
                "/"
            INDEX { hwSSUIndex }
            ::= { hwSSUTable 1 }

        HwSSUEntry            ::= SEQUENCE {
                hwSSUIndex
                    Integer32,
                hwSSUEquipId
                    Unsigned32,
                hwSSUEquipName
                    OCTET STRING,
                hwSSUInputVoltage
                    Unsigned32,
                hwSSUOutputVoltage
                    Unsigned32,
                hwSSUOutputCurrent
                    Unsigned32
            }

        hwSSUIndex OBJECT-TYPE
            SYNTAX Integer32 (0..256)
            MAX-ACCESS read-only
            STATUS current
            DESCRIPTION
                "SSU table index,which value range:1 to 256. Lines of the device list are restricted by the quantity of SSU."
            ::= { hwSSUEntry 1 }

        hwSSUEquipId OBJECT-TYPE
            SYNTAX Unsigned32 (24001..24255)
            MAX-ACCESS read-only
            STATUS current
            DESCRIPTION
                "SSU device ID. Value range: 024'001 to 024'255, in which the first digits indicate the device type and the last three digits indicate the device SN."
            ::= { hwSSUEntry 2 }

        hwSSUEquipName OBJECT-TYPE
            SYNTAX OCTET STRING (SIZE (0..63))
            MAX-ACCESS read-only
            STATUS current
            DESCRIPTION
                "Device name of the SSU module, character string type, is used to specify the SSU module. 
                Otherwise, the configured character can not be any other languages except English."
            ::= { hwSSUEntry 3 }

        hwSSUInputVoltage OBJECT-TYPE
            SYNTAX Unsigned32 (0..2000)
            MAX-ACCESS read-only
            STATUS current
            DESCRIPTION
                "The input voltage of SSU, 
                Value range: 0 to 200, 
                units: V, 
                and the value is one decimal space (.1)."
            ::= { hwSSUEntry 5 }

        hwSSUOutputVoltage OBJECT-TYPE
            SYNTAX Unsigned32 (0..2000)
            MAX-ACCESS read-only
            STATUS current
            DESCRIPTION
                "The output voltage of SSU, 
                Value range: 0 to 200, 
                units: V, 
                and the value is one decimal space (.1)."
            ::= { hwSSUEntry 6 }

        hwSSUOutputCurrent OBJECT-TYPE
            SYNTAX Unsigned32 (0..10000)
            MAX-ACCESS read-only
            STATUS current
            DESCRIPTION
                "The output current of SSU, 
                Value range: 0 to 1000, 
                units: A, 
                and the value is one decimal space (.1)."
            ::= { hwSSUEntry 7 }

        hwAcbGroupEquip OBJECT IDENTIFIER ::= { hwSiteMonitorMIBObjects 17 }

        hwAcbGroupSampTable OBJECT-TYPE
            SYNTAX SEQUENCE OF HwAcbGroupSampEntry
            MAX-ACCESS not-accessible
             STATUS current
             DESCRIPTION
                "/"
            ::= { hwAcbGroupEquip 1 }

        hwAcbGroupSampEntry OBJECT-TYPE
                        SYNTAX HwAcbGroupSampEntry
            MAX-ACCESS not-accessible
             STATUS current
             DESCRIPTION
                "/"
            INDEX { hwAcbGroupIndex }
            ::= { hwAcbGroupSampTable 1 }

        HwAcbGroupSampEntry            ::= SEQUENCE {
                hwAcbGroupIndex
                    Unsigned32,
                hwAcbGroupEquipId
                    Unsigned32,
                hwAcbGroupEquipName
                    OCTET STRING,
                hwAcbGroupBatRunningState
                    INTEGER,
                hwAcbGroupBatVolt
                    Unsigned32,
                hwAcbGroupBatCurr
                    Integer32,
                hwAcbGroupTotalCapacity
                    Unsigned32,
                hwAcbGroupTotalRemainCapacity
                    Unsigned32,
                hwAcbGroupTemperature
                    Integer32,
                hwAcbGroupBackupTime
                    Unsigned32,
                hwAcbGroupEsmuCommNum
                    Unsigned32,
                hwAcbGroupBatSoh
                    Unsigned32
            }

        hwAcbGroupIndex OBJECT-TYPE
            SYNTAX Unsigned32 (0..256)
            MAX-ACCESS read-only
            STATUS current
            DESCRIPTION
                "The battery group equip Index."
            ::= { hwAcbGroupSampEntry 1 }

        hwAcbGroupEquipId OBJECT-TYPE
            SYNTAX Unsigned32
            MAX-ACCESS read-only
            STATUS current
            DESCRIPTION
                "The battery group equip ID no."
            ::= { hwAcbGroupSampEntry 2 }

        hwAcbGroupEquipName OBJECT-TYPE
            SYNTAX OCTET STRING
            MAX-ACCESS read-only
            STATUS current
            DESCRIPTION
                "The battery group equip name."
            ::= { hwAcbGroupSampEntry 3 }

        hwAcbGroupBatRunningState OBJECT-TYPE
            SYNTAX INTEGER
                {
                firstOn(1),
                powerOff(2),
                float(3),
                equal(4),
                dicharge(5),
                charge(6),
                test(7),
                unknown(255)
                }
            MAX-ACCESS read-only
            STATUS current
            DESCRIPTION
                "State of the Battery group unit running state. It is an enumeration type: 
                  If the enumeration value is 1, it indicates the Battery is first on line; 
                  If the enumeration value is 2, it indicates that Battery power off; 
                  If the enumeration value is 3, it indicates  that Battery is on float charging; 
                  If the enumeration value is 4, it indicates that Battery is on equal charging; 
                  If the enumeration value is 5, it indicates that Battery is on discharge; 
                  If the enumeration value is 6, it indicates that Battery is on charge; 
                  If the enumeration value is 7, it indicates that Battery is on test; 
                  If the enumeration value is 255,  it indicates Battery uint operation status unknown. 
                "
            ::= { hwAcbGroupSampEntry 4 }

        hwAcbGroupBatVolt OBJECT-TYPE
            SYNTAX Unsigned32 (0..1000)
            MAX-ACCESS read-only
            STATUS current
            DESCRIPTION
                "The battery volt; Value range: 0 to 100, 
                units: V. 
                and the value is accurate to one decimal place (.1).  
                If the value is 2147483647(0x7FFFFFFF), it indicates that the value is invalid."
            ::= { hwAcbGroupSampEntry 5 }

        hwAcbGroupBatCurr OBJECT-TYPE
            SYNTAX Integer32 (-40000..40000)
            MAX-ACCESS read-only
            STATUS current
            DESCRIPTION
                "The battery current; Value range: -4000 to 4000, 
                units: A. 
                and the value is accurate to one decimal place (.1).  
                If the value is 2147483647(0x7FFFFFFF), it indicates that the value is invalid."
            ::= { hwAcbGroupSampEntry 6 }

        hwAcbGroupTotalCapacity OBJECT-TYPE
            SYNTAX Unsigned32 (0..100000)
            MAX-ACCESS read-only
            STATUS current
            DESCRIPTION
                "The battery total capacity; Value range: 0 to 10000, 
                units: Ah. 
                and the value is accurate to one decimal place (.1).   
                If the value is 2147483647(0x7FFFFFFF), it indicates that the value is invalid."
            ::= { hwAcbGroupSampEntry 7 }

        hwAcbGroupTotalRemainCapacity OBJECT-TYPE
            SYNTAX Unsigned32 (0..1000)
            MAX-ACCESS read-only
            STATUS current
            DESCRIPTION
                "The battery total remain capacity; Value range:0 to 100, 
                units: %. 
                and the value is accurate to one decimal place (.1).   
                If the value is 2147483647(0x7FFFFFFF), it indicates that the value is invalid."
            ::= { hwAcbGroupSampEntry 8 }

        hwAcbGroupTemperature OBJECT-TYPE
            SYNTAX Integer32 (-500..1000)
            MAX-ACCESS read-only
            STATUS current
            DESCRIPTION
                "The battery temperature; Value range:-50 to 100, 
                units: degC. 
                and the value is accurate to one decimal place (.1).   
                If the value is 2147483647(0x7FFFFFFF), it indicates that the value is invalid."
            ::= { hwAcbGroupSampEntry 9 }

        hwAcbGroupBackupTime OBJECT-TYPE
            SYNTAX Unsigned32 (0..2560)
            MAX-ACCESS read-only
            STATUS current
            DESCRIPTION
                "The battery backup time; Value range: 0 to 256, 
                units: h.
                and the value is accurate to one decimal place (.1).   
                If the value is 2147483647(0x7FFFFFFF), it indicates that the value is invalid."
            ::= { hwAcbGroupSampEntry 11 }

        hwAcbGroupEsmuCommNum OBJECT-TYPE
            SYNTAX Unsigned32 (0..100)
            MAX-ACCESS read-only
            STATUS current
            DESCRIPTION
                "The esmu communicate number; 
                Value range: 0 to 100.   
                If the value is 2147483647(0x7FFFFFFF), it indicates that the value is invalid."
            ::= { hwAcbGroupSampEntry 12 }

        hwAcbGroupBatSoh OBJECT-TYPE
            SYNTAX Unsigned32 (0..100)
            MAX-ACCESS read-only
            STATUS current
            DESCRIPTION
                "The battery soh: 0 to 100,  
                units: %. 
                and the value is accurate to one decimal place (1).   
                If the value is 2147483647(0x7FFFFFFF), it indicates that the value is invalid."
            ::= { hwAcbGroupSampEntry 13 }

        hwAcbGroupSetTable OBJECT-TYPE
            SYNTAX SEQUENCE OF HwAcbGroupSetEntry
            MAX-ACCESS not-accessible
             STATUS current
             DESCRIPTION
                "/"
            ::= { hwAcbGroupEquip 2 }

        hwAcbGroupSetEntry OBJECT-TYPE
                        SYNTAX HwAcbGroupSetEntry
            MAX-ACCESS not-accessible
             STATUS current
             DESCRIPTION
                "/"
            INDEX { hwAcbGroupCellNum }
            ::= { hwAcbGroupSetTable 1 }

        HwAcbGroupSetEntry            ::= SEQUENCE {
                hwAcbGroupCellNum
                    Unsigned32,
                hwAcbGroupEqualVolt
                    Unsigned32,
                hwAcbGroupFloatVolt
                    Unsigned32,
                hwAcbGroupChargeCurrLimitThr
                    Unsigned32,
                hwAcbGroupOverCurThr
                    Unsigned32,
                hwAcbGroupHighTempThr
                    Unsigned32,
                hwAcbGroupLowTempThr
                    Integer32
            }

        hwAcbGroupCellNum OBJECT-TYPE
            SYNTAX Unsigned32 (1..16)
            MAX-ACCESS read-write
            STATUS current
            DESCRIPTION
                "Battery cell number, can be configued by users. 
                Value range: 1 to 16, 
                If the value is 2147483647(0x7FFFFFFF), it indicates that the value is invalid. 
                The default value is 16."
            ::= { hwAcbGroupSetEntry 5 }

        hwAcbGroupEqualVolt OBJECT-TYPE
            SYNTAX Unsigned32 (420..580)
            MAX-ACCESS read-write
            STATUS current
            DESCRIPTION
                "Battery equalcharge  voltage, can be configued by users. 
                Value range: 42 to 58, 
                units: v, 
                and the value is accurate to one decimal space (.1).  
                If the value is 2147483647(0x7FFFFFFF), it indicates that the value is invalid. 
                The default value is 56.4. "
            ::= { hwAcbGroupSetEntry 11 }

        hwAcbGroupFloatVolt OBJECT-TYPE
            SYNTAX Unsigned32 (420..580)
            MAX-ACCESS read-write
            STATUS current
            DESCRIPTION
                "Battery floatcharge voltage, can be configued by users. 
                Value range: 42 to 58, 
                units: v, 
                and the value is accurate to one decimal space (.1).  
                If the value is 2147483647(0x7FFFFFFF), it indicates that the value is invalid. 
                The default value is 54.5. "
            ::= { hwAcbGroupSetEntry 12 }

        hwAcbGroupChargeCurrLimitThr OBJECT-TYPE
            SYNTAX Unsigned32 (5..200)
            MAX-ACCESS read-write
            STATUS current
            DESCRIPTION
                "Battery charge limited threhold , can be configued by users. 
                Value range: 0.05 to 2, 
                units: C10, 
                and the value is accurate to one decimal space (.01).  
                If the value is 2147483647(0x7FFFFFFF), it indicates that the value is invalid. 
                The default value is 0.4. 
                If the setting returns an error, it means that the current setting value is not supported."
            ::= { hwAcbGroupSetEntry 13 }

        hwAcbGroupOverCurThr OBJECT-TYPE
            SYNTAX Unsigned32 (15..120)
            MAX-ACCESS read-write
            STATUS current
            DESCRIPTION
                "Battery over charge current limited threhold , can be configued by users. 
                Value range: 0.15 to 1.2, 
                units: C10, 
                and the value is accurate to one decimal space (.01).  
                If the value is 2147483647(0x7FFFFFFF), it indicates that the value is invalid.
                The default value is 0.75. "
            ::= { hwAcbGroupSetEntry 14 }

        hwAcbGroupHighTempThr OBJECT-TYPE
            SYNTAX Unsigned32 (35..70)
            MAX-ACCESS read-write
            STATUS current
            DESCRIPTION
                "Upper threshold of the environment temperature alarm, can be configured by users. 
                Value range: 35 to 70, 
                units: centigrade (°C), 
                and the value is an integer (1).  
                If the value is 2147483647(0x7FFFFFFF), it indicates that the value is invalid. 
                The default value is 50."
            ::= { hwAcbGroupSetEntry 21 }

        hwAcbGroupLowTempThr OBJECT-TYPE
            SYNTAX Integer32 (-50..10)
            MAX-ACCESS read-write
            STATUS current
            DESCRIPTION
                "Lower threshold of the environment temperature alarm, can be configured by users. 
                Value range: -50 to 10, 
                units: centigrade (degC), 
                and the value is an integer (1).  
                If the value is 2147483647(0x7FFFFFFF), it indicates that the value is invalid. 
                The default value is 0."
            ::= { hwAcbGroupSetEntry 22 }

        hwAcbEquip OBJECT IDENTIFIER ::= { hwAcbGroupEquip 18 }

        hwAcbBaseTable OBJECT-TYPE
            SYNTAX SEQUENCE OF HwAcbBaseEntry
            MAX-ACCESS not-accessible
             STATUS current
             DESCRIPTION
                "/"
            ::= { hwAcbEquip 1 }

        hwAcbBaseEntry OBJECT-TYPE
                        SYNTAX HwAcbBaseEntry
            MAX-ACCESS not-accessible
             STATUS current
             DESCRIPTION
                "/"
            INDEX { hwAcbIndex }
            ::= { hwAcbBaseTable 1 }

        HwAcbBaseEntry            ::= SEQUENCE {
                hwAcbIndex
                    Unsigned32,
                hwAcbEquipId
                    Unsigned32,
                hwAcbEquipName
                    OCTET STRING,
                hwAcbEquipAddr
                    Unsigned32,
                hwAcbSoftVar
                    OCTET STRING
            }

        hwAcbIndex OBJECT-TYPE
            SYNTAX Unsigned32 (3668..3715  )
            MAX-ACCESS read-only
            STATUS current
            DESCRIPTION
                "The battery equip Index.Value range: 3668..3715  "
            ::= { hwAcbBaseEntry 1 }

        hwAcbEquipId OBJECT-TYPE
            SYNTAX Unsigned32
            MAX-ACCESS read-only
            STATUS current
            DESCRIPTION
                "The battery equip ID no.Value range: 31001 to 31032.  "
            ::= { hwAcbBaseEntry 2 }

        hwAcbEquipName OBJECT-TYPE
            SYNTAX OCTET STRING (SIZE (0..63))
            MAX-ACCESS read-only
            STATUS current
            DESCRIPTION
                "The battery equip name."
            ::= { hwAcbBaseEntry 3 }

        hwAcbEquipAddr OBJECT-TYPE
            SYNTAX Unsigned32 (0..255)
            MAX-ACCESS read-only
            STATUS current
            DESCRIPTION
                "The battery communica address."
            ::= { hwAcbBaseEntry 4 }

        hwAcbSoftVar OBJECT-TYPE
            SYNTAX OCTET STRING (SIZE (0..5))
            MAX-ACCESS read-only
            STATUS current
            DESCRIPTION
                "The Battery software version."
            ::= { hwAcbBaseEntry 5 }

        hwAcbSampTable OBJECT-TYPE
            SYNTAX SEQUENCE OF HwAcbSampEntry
            MAX-ACCESS not-accessible
             STATUS current
             DESCRIPTION
                "/"
            ::= { hwAcbEquip 2 }

        hwAcbSampEntry OBJECT-TYPE
                        SYNTAX HwAcbSampEntry
            MAX-ACCESS not-accessible
             STATUS current
             DESCRIPTION
                "/"
            INDEX { hwAcbBatVolt }
            ::= { hwAcbSampTable 1 }

        HwAcbSampEntry            ::= SEQUENCE {
                hwAcbBatVolt
                    Unsigned32,
                hwAcbBatCurr
                    Integer32,
                hwAcbRunningStatus
                    INTEGER,
                hwAcbBatSoh
                    Integer32,
                hwAcbBatCapacity
                    Integer32,
                hwAcbBatCell1Volt
                    Unsigned32,
                hwAcbBatCell2Volt
                    Unsigned32,
                hwAcbBatCell3Volt
                    Unsigned32,
                hwAcbBatCell4Volt
                    Unsigned32,
                hwAcbBatCell5Volt
                    Unsigned32,
                hwAcbBatCell6Volt
                    Unsigned32,
                hwAcbBatCell7Volt
                    Unsigned32,
                hwAcbBatCell8Volt
                    Unsigned32,
                hwAcbBatCell9Volt
                    Unsigned32,
                hwAcbBatCell10Volt
                    Unsigned32,
                hwAcbBatCell11Volt
                    Unsigned32,
                hwAcbBatCell12Volt
                    Unsigned32,
                hwAcbBatCell13Volt
                    Unsigned32,
                hwAcbBatCell14Volt
                    Unsigned32,
                hwAcbBatCell15Volt
                    Unsigned32,
                hwAcbBatCell16Volt
                    Unsigned32,
                hwAcbBatCell1Temp
                    Integer32,
                hwAcbBatCell2Temp
                    Integer32,
                hwAcbBatCell3Temp
                    Integer32,
                hwAcbBatCell4Temp
                    Integer32,
                hwAcbBatCell5Temp
                    Integer32,
                hwAcbBatCell6Temp
                    Integer32,
                hwAcbBatCell7Temp
                    Integer32,
                hwAcbBatCell8Temp
                    Integer32,
                hwAcbBatCell9Temp
                    Integer32,
                hwAcbBatCell10Temp
                    Integer32,
                hwAcbBatCell11Temp
                    Integer32,
                hwAcbBatCell12Temp
                    Integer32,
                hwAcbBatCell13Temp
                    Integer32,
                hwAcbBatCell14Temp
                    Integer32,
                hwAcbBatCell15Temp
                    Integer32,
                hwAcbBatCell16Temp
                    Integer32,
                hwAcbBatCell17Temp
                    Integer32,
                hwAcbBatCell18Temp
                    Integer32,
                hwAcbBatCell19Temp
                    Integer32,
                hwAcbBatCell20Temp
                    Integer32,
                hwAcbBatCell21Temp
                    Integer32,
                hwAcbBatCell22Temp
                    Integer32,
                hwAcbBatCell17Volt
                    Unsigned32,
                hwAcbBatCell18Volt
                    Unsigned32,
                hwAcbBatCell19Volt
                    Unsigned32,
                hwAcbBatCell20Volt
                    Unsigned32,
                hwAcbBatCell21Volt
                    Unsigned32,
                hwAcbBatCell22Volt
                    Unsigned32
            }

        hwAcbBatVolt OBJECT-TYPE
            SYNTAX Unsigned32 (0..600)
            MAX-ACCESS read-only
            STATUS current
            DESCRIPTION
                "voltage of the battery. It indicates the real-time statistics of the battery on the site. 
                Value range: 0 to 60, 
                unit: V, 
                and the value is accurate to one decimal place (.1).  
                If the value is 2147483647(0x7FFFFFFF), it indicates that the value is invalid."
            ::= { hwAcbSampEntry 1 }

        hwAcbBatCurr OBJECT-TYPE
            SYNTAX Integer32 (-2000..2000)
            MAX-ACCESS read-only
            STATUS current
            DESCRIPTION
                "Current of the battery. It indicates the real-time statistics of the battery on the site. 
                Value range: -200 to 200, 
                unit: A, 
                and the value is accurate to one decimal place (.1).  
                If the value is 2147483647(0x7FFFFFFF), it indicates that the value is invalid."
            ::= { hwAcbSampEntry 2 }

        hwAcbRunningStatus OBJECT-TYPE
            SYNTAX INTEGER
                {
                offline(1),
                online(2),
                sleep(3),
                disconnect(4),
                charge(5),
                discharge(6),
                standby(7),
                unknown(255)
                }
            MAX-ACCESS read-only
            STATUS current
            DESCRIPTION
                "Battery charging state, indicates the charging and discharging information about the battery group. It is an enumeration type. 
                If the enumeration value is 1, it indicates a battery  in the Offline state. 
                If the enumeration value is 2, it indicates a battery  in the online state. 
                If the enumeration value is 3, it indicates a battery  in the Sleep state. 
                If the enumeration value is 4, it indicates a battery  in the disconnect state. 
                If the enumeration value is 5, it indicates a battery  in the Charge state. 
                If the enumeration value is 6, it indicates a battery  in the Discharge state. 
                If the enumeration value is 7, it indicates a battery  in the Standby state. 
                If the enumeration value is 255, it indicates a battery group in the unknown state. "
            ::= { hwAcbSampEntry 3 }

        hwAcbBatSoh OBJECT-TYPE
            SYNTAX Integer32 (0..100)
            MAX-ACCESS read-only
            STATUS current
            DESCRIPTION
                "Soh of the battery. It indicates the real-time statistics of the battery on the site. 
                Value range: 0 to 100, 
                unit: %,
                and the value is accurate to two decimal place (1).   
                If the value is 2147483647(0x7FFFFFFF), it indicates that the value is invalid."
            ::= { hwAcbSampEntry 4 }

        hwAcbBatCapacity OBJECT-TYPE
            SYNTAX Integer32 (0..100000)
            MAX-ACCESS read-only
            STATUS current
            DESCRIPTION
                "Capacity of the battery.
                Value range: 0 to 10000, 
                unit: Ah, 
                and the value is accurate to two decimal place (.01).  
                If the value is 2147483647(0x7FFFFFFF), it indicates that the value is invalid."
            ::= { hwAcbSampEntry 5 }

        hwAcbBatCell1Volt OBJECT-TYPE
            SYNTAX Unsigned32 (0..50)
            MAX-ACCESS read-only
            STATUS current
            DESCRIPTION
                "Voltage of the battery cell. It indicates the real-time statistics of the battery on the site. 
                Value range: 0 to 5, 
                unit: V, 
                and the value is accurate to one decimal place (.1).  
                If the value is 2147483647(0x7FFFFFFF), it indicates that the value is invalid."
            ::= { hwAcbSampEntry 6 }

        hwAcbBatCell2Volt OBJECT-TYPE
            SYNTAX Unsigned32 (0..50)
            MAX-ACCESS read-only
            STATUS current
            DESCRIPTION
                "Voltage of the battery cell. It indicates the real-time statistics of the battery on the site. 
                Value range: 0 to 5, 
                unit: V, 
                and the value is accurate to one decimal place (.1).  
                If the value is 2147483647(0x7FFFFFFF), it indicates that the value is invalid."
            ::= { hwAcbSampEntry 7 }

        hwAcbBatCell3Volt OBJECT-TYPE
            SYNTAX Unsigned32 (0..50)
            MAX-ACCESS read-only
            STATUS current
            DESCRIPTION
                "Voltage of the battery cell. It indicates the real-time statistics of the battery on the site. 
                Value range: 0 to 5, 
                unit: V, 
                and the value is accurate to one decimal place (.1).  
                If the value is 2147483647(0x7FFFFFFF), it indicates that the value is invalid."
            ::= { hwAcbSampEntry 8 }

        hwAcbBatCell4Volt OBJECT-TYPE
            SYNTAX Unsigned32 (0..50)
            MAX-ACCESS read-only
            STATUS current
            DESCRIPTION
                "Voltage of the battery cell. It indicates the real-time statistics of the battery on the site. 
                Value range: 0 to 5, 
                unit: V, 
                and the value is accurate to one decimal place (.1).  
                If the value is 2147483647(0x7FFFFFFF), it indicates that the value is invalid."
            ::= { hwAcbSampEntry 9 }

        hwAcbBatCell5Volt OBJECT-TYPE
            SYNTAX Unsigned32 (0..50)
            MAX-ACCESS read-only
            STATUS current
            DESCRIPTION
                "Voltage of the battery cell. It indicates the real-time statistics of the battery on the site. 
                Value range: 0 to 5, 
                unit: V, 
                and the value is accurate to one decimal place (.1).  
                If the value is 2147483647(0x7FFFFFFF), it indicates that the value is invalid."
            ::= { hwAcbSampEntry 10 }

        hwAcbBatCell6Volt OBJECT-TYPE
            SYNTAX Unsigned32 (0..50)
            MAX-ACCESS read-only
            STATUS current
            DESCRIPTION
                "Voltage of the battery cell. It indicates the real-time statistics of the battery on the site. 
                Value range: 0 to 5, 
                unit: V, 
                and the value is accurate to one decimal place (.1).  
                If the value is 2147483647(0x7FFFFFFF), it indicates that the value is invalid."
            ::= { hwAcbSampEntry 11 }

        hwAcbBatCell7Volt OBJECT-TYPE
            SYNTAX Unsigned32 (0..50)
            MAX-ACCESS read-only
            STATUS current
            DESCRIPTION
                "Voltage of the battery cell. It indicates the real-time statistics of the battery on the site. 
                Value range: 0 to 5, 
                unit: V, 
                and the value is accurate to one decimal place (.1).  
                If the value is 2147483647(0x7FFFFFFF), it indicates that the value is invalid."
            ::= { hwAcbSampEntry 12 }

        hwAcbBatCell8Volt OBJECT-TYPE
            SYNTAX Unsigned32 (0..50)
            MAX-ACCESS read-only
            STATUS current
            DESCRIPTION
                "Voltage of the battery cell. It indicates the real-time statistics of the battery on the site. 
                Value range: 0 to 5, 
                unit: V, 
                and the value is accurate to one decimal place (.1).  
                If the value is 2147483647(0x7FFFFFFF), it indicates that the value is invalid."
            ::= { hwAcbSampEntry 13 }

        hwAcbBatCell9Volt OBJECT-TYPE
            SYNTAX Unsigned32 (0..50)
            MAX-ACCESS read-only
            STATUS current
            DESCRIPTION
                "Voltage of the battery cell. It indicates the real-time statistics of the battery on the site. 
                Value range: 0 to 5, 
                unit: V, 
                and the value is accurate to one decimal place (.1).  
                If the value is 2147483647(0x7FFFFFFF), it indicates that the value is invalid."
            ::= { hwAcbSampEntry 14 }

        hwAcbBatCell10Volt OBJECT-TYPE
            SYNTAX Unsigned32 (0..50)
            MAX-ACCESS read-only
            STATUS current
            DESCRIPTION
                "Voltage of the battery cell. It indicates the real-time statistics of the battery on the site. 
                Value range: 0 to 5, 
                unit: V, 
                and the value is accurate to one decimal place (.1).  
                If the value is 2147483647(0x7FFFFFFF), it indicates that the value is invalid."
            ::= { hwAcbSampEntry 15 }

        hwAcbBatCell11Volt OBJECT-TYPE
            SYNTAX Unsigned32 (0..50)
            MAX-ACCESS read-only
            STATUS current
            DESCRIPTION
                "Voltage of the battery cell. It indicates the real-time statistics of the battery on the site. 
                Value range: 0 to 5, 
                unit: V, 
                and the value is accurate to one decimal place (.1).  
                If the value is 2147483647(0x7FFFFFFF), it indicates that the value is invalid."
            ::= { hwAcbSampEntry 16 }

        hwAcbBatCell12Volt OBJECT-TYPE
            SYNTAX Unsigned32 (0..50)
            MAX-ACCESS read-only
            STATUS current
            DESCRIPTION
                "Voltage of the battery cell. It indicates the real-time statistics of the battery on the site. 
                Value range: 0 to 5, 
                unit: V, 
                and the value is accurate to one decimal place (.1).  
                If the value is 2147483647(0x7FFFFFFF), it indicates that the value is invalid."
            ::= { hwAcbSampEntry 17 }

        hwAcbBatCell13Volt OBJECT-TYPE
            SYNTAX Unsigned32 (0..50)
            MAX-ACCESS read-only
            STATUS current
            DESCRIPTION
                "Voltage of the battery cell. It indicates the real-time statistics of the battery on the site. 
                Value range: 0 to 5, 
                unit: V, 
                and the value is accurate to one decimal place (.1).  
                If the value is 2147483647(0x7FFFFFFF), it indicates that the value is invalid."
            ::= { hwAcbSampEntry 18 }

        hwAcbBatCell14Volt OBJECT-TYPE
            SYNTAX Unsigned32 (0..50)
            MAX-ACCESS read-only
            STATUS current
            DESCRIPTION
                "Voltage of the battery cell. It indicates the real-time statistics of the battery on the site. 
                Value range: 0 to 5, 
                unit: V, 
                and the value is accurate to one decimal place (.1).  
                If the value is 2147483647(0x7FFFFFFF), it indicates that the value is invalid."
            ::= { hwAcbSampEntry 19 }

        hwAcbBatCell15Volt OBJECT-TYPE
            SYNTAX Unsigned32 (0..50)
            MAX-ACCESS read-only
            STATUS current
            DESCRIPTION
                "Voltage of the battery cell. It indicates the real-time statistics of the battery on the site. 
                Value range: 0 to 5, 
                unit: V, 
                and the value is accurate to one decimal place (.1).  
                If the value is 2147483647(0x7FFFFFFF), it indicates that the value is invalid."
            ::= { hwAcbSampEntry 20 }

        hwAcbBatCell16Volt OBJECT-TYPE
            SYNTAX Unsigned32 (0..50)
            MAX-ACCESS read-only
            STATUS current
            DESCRIPTION
                "Voltage of the battery cell. It indicates the real-time statistics of the battery on the site. 
                Value range: 0 to 5, 
                unit: V, 
                and the value is accurate to one decimal place (.1).  
                If the value is 2147483647(0x7FFFFFFF), it indicates that the value is invalid."
            ::= { hwAcbSampEntry 21 }

        hwAcbBatCell1Temp OBJECT-TYPE
            SYNTAX Integer32 (-1000..1000)
            MAX-ACCESS read-only
            STATUS current
            DESCRIPTION
                "Temperature of the battery cell. It indicates the real-time statistics of the battery on the site. 
                Value range: -100 to 100, 
                unit: degC, 
                and the value is accurate to one decimal place (.1).  
                If the value is 2147483647(0x7FFFFFFF), it indicates that the value is invalid."
            ::= { hwAcbSampEntry 22 }

        hwAcbBatCell2Temp OBJECT-TYPE
            SYNTAX Integer32 (-1000..1000)
            MAX-ACCESS read-only
            STATUS current
            DESCRIPTION
                "Temperature of the battery cell. It indicates the real-time statistics of the battery on the site. 
                Value range: -100 to 100, 
                unit: degC, 
                and the value is accurate to one decimal place (.1).  
                If the value is 2147483647(0x7FFFFFFF), it indicates that the value is invalid."
            ::= { hwAcbSampEntry 23 }

        hwAcbBatCell3Temp OBJECT-TYPE
            SYNTAX Integer32 (-1000..1000)
            MAX-ACCESS read-only
            STATUS current
            DESCRIPTION
                "Temperature of the battery cell. It indicates the real-time statistics of the battery on the site. 
                Value range: -100 to 100, 
                unit: degC, 
                and the value is accurate to one decimal place (.1).  
                If the value is 2147483647(0x7FFFFFFF), it indicates that the value is invalid."
            ::= { hwAcbSampEntry 24 }

        hwAcbBatCell4Temp OBJECT-TYPE
            SYNTAX Integer32 (-1000..1000)
            MAX-ACCESS read-only
            STATUS current
            DESCRIPTION
                "Temperature of the battery cell. It indicates the real-time statistics of the battery on the site. 
                Value range: -100 to 100, 
                unit: degC, 
                and the value is accurate to one decimal place (.1).  
                If the value is 2147483647(0x7FFFFFFF), it indicates that the value is invalid."
            ::= { hwAcbSampEntry 25 }

        hwAcbBatCell5Temp OBJECT-TYPE
            SYNTAX Integer32 (-1000..1000)
            MAX-ACCESS read-only
            STATUS current
            DESCRIPTION
                "Temperature of the battery cell. It indicates the real-time statistics of the battery on the site. 
                Value range: -100 to 100, 
                unit: degC, 
                and the value is accurate to one decimal place (.1).  
                If the value is 2147483647(0x7FFFFFFF), it indicates that the value is invalid."
            ::= { hwAcbSampEntry 26 }

        hwAcbBatCell6Temp OBJECT-TYPE
            SYNTAX Integer32 (-1000..1000)
            MAX-ACCESS read-only
            STATUS current
            DESCRIPTION
                "Temperature of the battery cell. It indicates the real-time statistics of the battery on the site. 
                Value range: -100 to 100, 
                unit: degC, 
                and the value is accurate to one decimal place (.1).  
                If the value is 2147483647(0x7FFFFFFF), it indicates that the value is invalid."
            ::= { hwAcbSampEntry 27 }

        hwAcbBatCell7Temp OBJECT-TYPE
            SYNTAX Integer32 (-1000..1000)
            MAX-ACCESS read-only
            STATUS current
            DESCRIPTION
                "Temperature of the battery cell. It indicates the real-time statistics of the battery on the site. 
                Value range: -100 to 100, 
                unit: degC, 
                and the value is accurate to one decimal place (.1).  
                If the value is 2147483647(0x7FFFFFFF), it indicates that the value is invalid."
            ::= { hwAcbSampEntry 28 }

        hwAcbBatCell8Temp OBJECT-TYPE
            SYNTAX Integer32 (-1000..1000)
            MAX-ACCESS read-only
            STATUS current
            DESCRIPTION
                "Temperature of the battery cell. It indicates the real-time statistics of the battery on the site. 
                Value range: -100 to 100, 
                unit: degC, 
                and the value is accurate to one decimal place (.1).  
                If the value is 2147483647(0x7FFFFFFF), it indicates that the value is invalid."
            ::= { hwAcbSampEntry 29 }

        hwAcbBatCell9Temp OBJECT-TYPE
            SYNTAX Integer32 (-1000..1000)
            MAX-ACCESS read-only
            STATUS current
            DESCRIPTION
                "Temperature of the battery cell. It indicates the real-time statistics of the battery on the site. 
                Value range: -100 to 100, 
                unit: degC, 
                and the value is accurate to one decimal place (.1).  
                If the value is 2147483647(0x7FFFFFFF), it indicates that the value is invalid."
            ::= { hwAcbSampEntry 30 }

        hwAcbBatCell10Temp OBJECT-TYPE
            SYNTAX Integer32 (-1000..1000)
            MAX-ACCESS read-only
            STATUS current
            DESCRIPTION
                "Temperature of the battery cell. It indicates the real-time statistics of the battery on the site. 
                Value range: -100 to 100, 
                unit: degC, 
                and the value is accurate to one decimal place (.1).  
                If the value is 2147483647(0x7FFFFFFF), it indicates that the value is invalid."
            ::= { hwAcbSampEntry 31 }

        hwAcbBatCell11Temp OBJECT-TYPE
            SYNTAX Integer32 (-1000..1000)
            MAX-ACCESS read-only
            STATUS current
            DESCRIPTION
                "Temperature of the battery cell. It indicates the real-time statistics of the battery on the site. 
                Value range: -100 to 100, 
                unit: degC, 
                and the value is accurate to one decimal place (.1).  
                If the value is 2147483647(0x7FFFFFFF), it indicates that the value is invalid."
            ::= { hwAcbSampEntry 32 }

        hwAcbBatCell12Temp OBJECT-TYPE
            SYNTAX Integer32 (-1000..1000)
            MAX-ACCESS read-only
            STATUS current
            DESCRIPTION
                "Temperature of the battery cell. It indicates the real-time statistics of the battery on the site. 
                Value range: -100 to 100, 
                unit: degC, 
                and the value is accurate to one decimal place (.1).  
                If the value is 2147483647(0x7FFFFFFF), it indicates that the value is invalid."
            ::= { hwAcbSampEntry 33 }

        hwAcbBatCell13Temp OBJECT-TYPE
            SYNTAX Integer32 (-1000..1000)
            MAX-ACCESS read-only
            STATUS current
            DESCRIPTION
                "Temperature of the battery cell. It indicates the real-time statistics of the battery on the site. 
                Value range: -100 to 100, 
                unit: degC, 
                and the value is accurate to one decimal place (.1).  
                If the value is 2147483647(0x7FFFFFFF), it indicates that the value is invalid."
            ::= { hwAcbSampEntry 34 }

        hwAcbBatCell14Temp OBJECT-TYPE
            SYNTAX Integer32 (-1000..1000)
            MAX-ACCESS read-only
            STATUS current
            DESCRIPTION
                "Temperature of the battery cell. It indicates the real-time statistics of the battery on the site. 
                Value range: -100 to 100, 
                unit: degC, 
                and the value is accurate to one decimal place (.1).  
                If the value is 2147483647(0x7FFFFFFF), it indicates that the value is invalid."
            ::= { hwAcbSampEntry 35 }

        hwAcbBatCell15Temp OBJECT-TYPE
            SYNTAX Integer32 (-1000..1000)
            MAX-ACCESS read-only
            STATUS current
            DESCRIPTION
                "Temperature of the battery cell. It indicates the real-time statistics of the battery on the site. 
                Value range: -100 to 100, 
                unit: degC, 
                and the value is accurate to one decimal place (.1).  
                If the value is 2147483647(0x7FFFFFFF), it indicates that the value is invalid."
            ::= { hwAcbSampEntry 36 }

        hwAcbBatCell16Temp OBJECT-TYPE
            SYNTAX Integer32 (-1000..1000)
            MAX-ACCESS read-only
            STATUS current
            DESCRIPTION
                "Temperature of the battery cell. It indicates the real-time statistics of the battery on the site. 
                Value range: -100 to 100, 
                unit: degC, 
                and the value is accurate to one decimal place (.1).  
                If the value is 2147483647(0x7FFFFFFF), it indicates that the value is invalid."
            ::= { hwAcbSampEntry 37 }

        hwAcbBatCell17Temp OBJECT-TYPE
            SYNTAX Integer32 (-1000..1000)
            MAX-ACCESS read-only
            STATUS current
            DESCRIPTION
                "Temperature of the battery cell. It indicates the real-time statistics of the battery on the site. 
                Value range: -100 to 100, 
                units: centigrade(degC), 
                and the value is accurate to one decimal place (.1).  
                If the value is 2147483647(0x7FFFFFFF), it indicates that the value is invalid."
            ::= { hwAcbSampEntry 38 }

        hwAcbBatCell18Temp OBJECT-TYPE
            SYNTAX Integer32 (-1000..1000)
            MAX-ACCESS read-only
            STATUS current
            DESCRIPTION
                "Temperature of the battery cell. It indicates the real-time statistics of the battery on the site. 
                Value range: -100 to 100, 
                units: centigrade(degC), 
                and the value is accurate to one decimal place (.1).  
                If the value is 2147483647(0x7FFFFFFF), it indicates that the value is invalid."
            ::= { hwAcbSampEntry 39 }

        hwAcbBatCell19Temp OBJECT-TYPE
            SYNTAX Integer32 (-1000..1000)
            MAX-ACCESS read-only
            STATUS current
            DESCRIPTION
                "Temperature of the battery cell. It indicates the real-time statistics of the battery on the site. 
                Value range: -100 to 100, 
                units: centigrade(degC), 
                and the value is accurate to one decimal place (.1).  
                If the value is 2147483647(0x7FFFFFFF), it indicates that the value is invalid."
            ::= { hwAcbSampEntry 40 }

        hwAcbBatCell20Temp OBJECT-TYPE
            SYNTAX Integer32 (-1000..1000)
            MAX-ACCESS read-only
            STATUS current
            DESCRIPTION
                "Temperature of the battery cell. It indicates the real-time statistics of the battery on the site. 
                Value range: -100 to 100, 
                units: centigrade(degC), 
                and the value is accurate to one decimal place (.1).  
                If the value is 2147483647(0x7FFFFFFF), it indicates that the value is invalid."
            ::= { hwAcbSampEntry 41 }

        hwAcbBatCell21Temp OBJECT-TYPE
            SYNTAX Integer32 (-1000..1000)
            MAX-ACCESS read-only
            STATUS current
            DESCRIPTION
                "Temperature of the battery cell. It indicates the real-time statistics of the battery on the site. 
                Value range: -100 to 100, 
                units: centigrade(degC), 
                and the value is accurate to one decimal place (.1).  
                If the value is 2147483647(0x7FFFFFFF), it indicates that the value is invalid."
            ::= { hwAcbSampEntry 42 }

        hwAcbBatCell22Temp OBJECT-TYPE
            SYNTAX Integer32 (-1000..1000)
            MAX-ACCESS read-only
            STATUS current
            DESCRIPTION
                "Temperature of the battery cell. It indicates the real-time statistics of the battery on the site. 
                Value range: -100 to 100, 
                units: centigrade(degC), 
                and the value is accurate to one decimal place (.1).  
                If the value is 2147483647(0x7FFFFFFF), it indicates that the value is invalid."
            ::= { hwAcbSampEntry 43 }

        hwAcbBatCell17Volt OBJECT-TYPE
            SYNTAX Unsigned32 (0..50)
            MAX-ACCESS read-only
            STATUS current
            DESCRIPTION
                "Voltage of the battery cell. It indicates the real-time statistics of the battery on the site. 
                Value range: 0 to 5, 
                unit: V, 
                and the value is accurate to one decimal place (.1).  
                If the value is 2147483647(0x7FFFFFFF), it indicates that the value is invalid."
            ::= { hwAcbSampEntry 44 }

        hwAcbBatCell18Volt OBJECT-TYPE
            SYNTAX Unsigned32 (0..50)
            MAX-ACCESS read-only
            STATUS current
            DESCRIPTION
                "Voltage of the battery cell. It indicates the real-time statistics of the battery on the site. 
                Value range: 0 to 5, 
                unit: V, 
                and the value is accurate to one decimal place (.1).  
                If the value is 2147483647(0x7FFFFFFF), it indicates that the value is invalid."
            ::= { hwAcbSampEntry 45 }

        hwAcbBatCell19Volt OBJECT-TYPE
            SYNTAX Unsigned32 (0..50)
            MAX-ACCESS read-only
            STATUS current
            DESCRIPTION
                "Voltage of the battery cell. It indicates the real-time statistics of the battery on the site. 
                Value range: 0 to 5, 
                unit: V, 
                and the value is accurate to one decimal place (.1).  
                If the value is 2147483647(0x7FFFFFFF), it indicates that the value is invalid."
            ::= { hwAcbSampEntry 46 }

        hwAcbBatCell20Volt OBJECT-TYPE
            SYNTAX Unsigned32 (0..50)
            MAX-ACCESS read-only
            STATUS current
            DESCRIPTION
                "Voltage of the battery cell. It indicates the real-time statistics of the battery on the site. 
                Value range: 0 to 5, 
                unit: V, 
                and the value is accurate to one decimal place (.1).  
                If the value is 2147483647(0x7FFFFFFF), it indicates that the value is invalid."
            ::= { hwAcbSampEntry 47 }

        hwAcbBatCell21Volt OBJECT-TYPE
            SYNTAX Unsigned32 (0..50)
            MAX-ACCESS read-only
            STATUS current
            DESCRIPTION
                "Voltage of the battery cell. It indicates the real-time statistics of the battery on the site. 
                Value range: 0 to 5, 
                unit: V, 
                and the value is accurate to one decimal place (.1).  
                If the value is 2147483647(0x7FFFFFFF), it indicates that the value is invalid."
            ::= { hwAcbSampEntry 48 }

        hwAcbBatCell22Volt OBJECT-TYPE
            SYNTAX Unsigned32 (0..50)
            MAX-ACCESS read-only
            STATUS current
            DESCRIPTION
                "Voltage of the battery cell. It indicates the real-time statistics of the battery on the site. 
                Value range: 0 to 5, 
                unit: V, 
                and the value is accurate to one decimal place (.1).  
                If the value is 2147483647(0x7FFFFFFF), it indicates that the value is invalid."
            ::= { hwAcbSampEntry 49 }

        hwElockEquip OBJECT IDENTIFIER ::= { hwSiteMonitorMIBObjects 27 }

        hwElockEquipTable OBJECT-TYPE
            SYNTAX SEQUENCE OF HwElockEquipEntry
            MAX-ACCESS not-accessible
             STATUS current
             DESCRIPTION
                "/"
            ::= { hwElockEquip 1 }

        hwElockEquipEntry OBJECT-TYPE
                        SYNTAX HwElockEquipEntry
            MAX-ACCESS not-accessible
             STATUS current
             DESCRIPTION
                "/"
            INDEX { hwElockEquipIndex }
            ::= { hwElockEquipTable 1 }

        HwElockEquipEntry            ::= SEQUENCE {
                hwElockEquipIndex
                    Unsigned32,
                hwElockEquipId
                    Unsigned32,
                hwElockEquipName
                    OCTET STRING
            }

        hwElockEquipIndex OBJECT-TYPE
            SYNTAX Unsigned32 (0..256)
            MAX-ACCESS read-only
            STATUS current
            DESCRIPTION
                "The elock equip Index."
            ::= { hwElockEquipEntry 1 }

        hwElockEquipId OBJECT-TYPE
            SYNTAX Unsigned32
            MAX-ACCESS read-only
            STATUS current
            DESCRIPTION
                "The elock  equip ID no."
            ::= { hwElockEquipEntry 2 }

        hwElockEquipName OBJECT-TYPE
            SYNTAX OCTET STRING
            MAX-ACCESS read-only
            STATUS current
            DESCRIPTION
                " The elock equip name."
            ::= { hwElockEquipEntry 3 }

        hwTemHumEquip OBJECT IDENTIFIER ::= { hwSiteMonitorMIBObjects 28 }

        hwTemHumEquipTable OBJECT-TYPE
            SYNTAX SEQUENCE OF HwTemHumEquipEntry
            MAX-ACCESS not-accessible
             STATUS current
             DESCRIPTION
                "/"
            ::= { hwTemHumEquip 1 }

        hwTemHumEquipEntry OBJECT-TYPE
                        SYNTAX HwTemHumEquipEntry
            MAX-ACCESS not-accessible
             STATUS current
             DESCRIPTION
                "/"
            INDEX { hwTemHumEquipIndex }
            ::= { hwTemHumEquipTable 1 }

        HwTemHumEquipEntry            ::= SEQUENCE {
                hwTemHumEquipIndex
                    Unsigned32,
                hwTemHumEquipId
                    Unsigned32,
                hwTemHumEquipName
                    OCTET STRING
            }

        hwTemHumEquipIndex OBJECT-TYPE
            SYNTAX Unsigned32 (0..256)
            MAX-ACCESS read-only
            STATUS current
            DESCRIPTION
                "The tem_hum equip Index."
            ::= { hwTemHumEquipEntry 1 }

        hwTemHumEquipId OBJECT-TYPE
            SYNTAX Unsigned32
            MAX-ACCESS read-only
            STATUS current
            DESCRIPTION
                "The tem_hum  equip ID no."
            ::= { hwTemHumEquipEntry 2 }

        hwTemHumEquipName OBJECT-TYPE
            SYNTAX OCTET STRING
            MAX-ACCESS read-only
            STATUS current
            DESCRIPTION
                " The tem_hum equip name."
            ::= { hwTemHumEquipEntry 3 }

        hwSiteMonitorMIBTraps OBJECT IDENTIFIER ::= { hwSiteMonitorMIB 2 }

        hwSiteAlarmTraps OBJECT IDENTIFIER ::= { hwSiteMonitorMIBTraps 1 }

        hwSiteAlarmTrapsPrefix OBJECT IDENTIFIER ::= { hwSiteAlarmTraps 0 }

        hwRectifierFaultAlarmTraps NOTIFICATION-TYPE
            OBJECTS { hwAlarmTrapOrdinalNumber,hwAlarmText,hwAlarmLevel,hwAlarmSigDesc,hwSiteName,hwSiteAdminAddr,hwNetIdentifier,hwSiteDescription,hwRectEquipId,hwRectEquipName,hwRectOperStatus            }
            STATUS current
            DESCRIPTION
                "When rectifiers fault alarms happen, a alarm trap will be send. Its correlation binding parameters: Site ID, Site name, Site description, NE ID, Alarm name, Alarm single description, Alarm port description, Alarm severity, and Site alarm SN. 
                Additionally, in order to identify the device, rectifier equipment ID and equipment name are also include in VB(variable bondings)."
            ::= { hwSiteAlarmTrapsPrefix 1 }

        hwRectifierFaultAlarmResumeTraps NOTIFICATION-TYPE
            OBJECTS { hwAlarmTrapOrdinalNumber,hwAlarmText,hwAlarmLevel,hwAlarmSigDesc,hwSiteName,hwSiteAdminAddr,hwNetIdentifier,hwSiteDescription,hwRectEquipId,hwRectEquipName,hwRectOperStatus            }
            STATUS current
            DESCRIPTION
                "Rectifier Fault alarm resolved.Its correlation binding parameters: Site ID, Site name, Site description, NE ID, Alarm name, Alarm single description, Alarm port description, Alarm severity, and Site alarm SN. Additionally, in order to identify the device, rectifier equipment ID and equipment name are also include in VB(variable bondings)."
            ::= { hwSiteAlarmTrapsPrefix 2 }

        hwRectifierAbnormalAlarmTraps NOTIFICATION-TYPE
            OBJECTS { hwAlarmTrapOrdinalNumber,hwAlarmText,hwAlarmLevel,hwAlarmSigDesc,hwSiteName,hwSiteAdminAddr,hwNetIdentifier,hwSiteDescription,hwRectEquipId,hwRectEquipName,hwRectOperStatus            }
            STATUS current
            DESCRIPTION
                "Rectifier abnormal alarm, because of communication failure, module protection, or turnoff. Its correlation binding parameters:  
                Site ID, Site name, Site description, NE ID, Alarm name, Alarm single description, Alarm port description, Alarm severity, and Site alarm SN. Additionally, in order to identify the device, rectifier equipment ID and equipment name are also include in VB(variable bondings)."
            ::= { hwSiteAlarmTrapsPrefix 3 }

        hwRectifierAbnormalAlarmResumeTraps NOTIFICATION-TYPE
            OBJECTS { hwAlarmTrapOrdinalNumber,hwAlarmText,hwAlarmLevel,hwAlarmSigDesc,hwSiteName,hwSiteAdminAddr,hwNetIdentifier,hwSiteDescription,hwRectEquipId,hwRectEquipName,hwRectOperStatus            }
            STATUS current
            DESCRIPTION
                "Rectifier abnormal alarm resume. Description.Its correlation binding parameters:  Site ID, Site name, Site description, NE ID, Alarm name, Alarm single description, Alarm port description, Alarm severity, and Site alarm SN. Additionally, in order to identify the device, rectifier equipment ID and equipment name are also include in VB(variable bondings)."
            ::= { hwSiteAlarmTrapsPrefix 4 }

        hwBattLoopBreakAlarmTraps NOTIFICATION-TYPE
            OBJECTS { hwAlarmTrapOrdinalNumber,hwAlarmText,hwAlarmLevel,hwAlarmSigDesc,hwSiteName,hwSiteAdminAddr,hwNetIdentifier,hwSiteDescription,hwBattStringEquipId,hwBattStringEquipName,hwBattStringOperStatus            }
            STATUS current
            DESCRIPTION
                "Battery loop disconnect. Its correlation binding parameters:  Site ID, Site name, Site description, NE ID, Alarm name, Alarm single description, Alarm port description, Alarm severity, and Site alarm SN. Additionally, in order to identify the device, battery string equipment ID and equipment name are also include in VB(variable bondings)."
            ::= { hwSiteAlarmTrapsPrefix 5 }

        hwBattLoopBreakAlarmResumeTraps NOTIFICATION-TYPE
            OBJECTS { hwAlarmTrapOrdinalNumber,hwAlarmText,hwAlarmLevel,hwAlarmSigDesc,hwSiteName,hwSiteAdminAddr,hwNetIdentifier,hwSiteDescription,hwBattStringEquipId,hwBattStringEquipName,hwBattStringOperStatus            }
            STATUS current
            DESCRIPTION
                "Battery loop break alarm resume. Its correlation binding parameters:  Site ID, Site name, Site description, NE ID, Alarm name, Alarm single description, Alarm port description, Alarm severity, and Site alarm SN. Additionally, in order to identify the device, battery string equipment ID and equipment name are also include in VB(variable bondings)."
            ::= { hwSiteAlarmTrapsPrefix 6 }

        hwBattLvdAlarmTraps NOTIFICATION-TYPE
            OBJECTS { hwAlarmTrapOrdinalNumber,hwAlarmText,hwAlarmLevel,hwAlarmSigDesc,hwSiteName,hwSiteAdminAddr,hwNetIdentifier,hwSiteDescription,hwLvdUnitEquipId,hwLvdUnitEquipName,hwLvdBranchOperStatus            }
            STATUS current
            DESCRIPTION
                "Battery disconnect for low voltage. Its correlation binding parameters:  Site ID, Site name, Site description, NE ID, Alarm name, Alarm single description, Alarm port description, Alarm severity, and Site alarm SN. 
                Additionally, in order to identify the device, battery LVD unit equipment ID and equipment name are also include in VB(variable bondings)."
            ::= { hwSiteAlarmTrapsPrefix 7 }

        hwBattLvdAlarmResumeTraps NOTIFICATION-TYPE
            OBJECTS { hwAlarmTrapOrdinalNumber,hwAlarmText,hwAlarmLevel,hwAlarmSigDesc,hwSiteName,hwSiteAdminAddr,hwNetIdentifier,hwSiteDescription,hwLvdUnitEquipId,hwLvdUnitEquipName,hwLvdBranchOperStatus            }
            STATUS current
            DESCRIPTION
                "Battery LVD alarm resume. Its correlation binding parameters:  Site ID, Site name, Site description, NE ID, Alarm name, Alarm single description, Alarm port description, Alarm severity, and Site alarm SN. Additionally, in order to identify the device, battery LVD unit equipment ID and equipment name are also include in VB(variable bondings)."
            ::= { hwSiteAlarmTrapsPrefix 8 }

        hwBattOverCurrAlarmTraps NOTIFICATION-TYPE
            OBJECTS { hwAlarmTrapOrdinalNumber,hwAlarmText,hwAlarmLevel,hwAlarmSigDesc,hwSiteName,hwSiteAdminAddr,hwNetIdentifier,hwSiteDescription,hwBattStringEquipId,hwBattStringEquipName,hwBattStringOperStatus            }
            STATUS current
            DESCRIPTION
                "Batterys charge in over current. Its correlation binding parameters:  Site ID, Site name, Site description, NE ID, Alarm name, Alarm single description, Alarm port description, Alarm severity, and Site alarm SN. Additionally, in order to identify the device, battery string equipment ID and equipment name are also include in VB(variable bondings)."
            ::= { hwSiteAlarmTrapsPrefix 9 }

        hwBattOverCurrAlarmResumeTraps NOTIFICATION-TYPE
            OBJECTS { hwAlarmTrapOrdinalNumber,hwAlarmText,hwAlarmLevel,hwAlarmSigDesc,hwSiteName,hwSiteAdminAddr,hwNetIdentifier,hwSiteDescription,hwBattStringEquipId,hwBattStringEquipName,hwBattStringOperStatus            }
            STATUS current
            DESCRIPTION
                "Batterys over current alarm resume. Its correlation binding parameters:  Site ID, Site name, Site description, NE ID, Alarm name, Alarm single description, Alarm port description, Alarm severity, and Site alarm SN. Additionally, in order to identify the device, battery string equipment ID and equipment name are also include in VB(variable bondings)."
            ::= { hwSiteAlarmTrapsPrefix 10 }

        hwBattStringTempAlarmTraps NOTIFICATION-TYPE
            OBJECTS { hwAlarmTrapOrdinalNumber,hwAlarmText,hwAlarmLevel,hwAlarmSigDesc,hwSiteName,hwSiteAdminAddr,hwNetIdentifier,hwSiteDescription,hwBattStringEquipId,hwBattStringEquipName,hwBattStringOperStatus            }
            STATUS current
            DESCRIPTION
                "Battery string temperature is too high or too low. Its correlation binding parameters:  Site ID, Site name, Site description, NE ID, Alarm name, Alarm single description, Alarm port description, Alarm severity, and Site alarm SN. Additionally, in order to identify the device, battery group ID and group name are also include in VB(variable bondings)."
            ::= { hwSiteAlarmTrapsPrefix 11 }

        hwBattStringTempAlarmResumeTraps NOTIFICATION-TYPE
            OBJECTS { hwAlarmTrapOrdinalNumber,hwAlarmText,hwAlarmLevel,hwAlarmSigDesc,hwSiteName,hwSiteAdminAddr,hwNetIdentifier,hwSiteDescription,hwBattStringEquipId,hwBattStringEquipName,hwBattStringOperStatus            }
            STATUS current
            DESCRIPTION
                "Battery string temperature alarm resume. Its correlation binding parameters:  Site ID, Site name, Site description, NE ID, Alarm name, Alarm single description, Alarm port description, Alarm severity, and Site alarm SN. Additionally, in order to identify the device, battery group ID and group name are also include in VB(variable bondings)."
            ::= { hwSiteAlarmTrapsPrefix 12 }

        hwBattDischargeAlarmTraps NOTIFICATION-TYPE
            OBJECTS { hwAlarmTrapOrdinalNumber,hwAlarmText,hwAlarmLevel,hwAlarmSigDesc,hwSiteName,hwSiteAdminAddr,hwNetIdentifier,hwSiteDescription,hwBattsGroupId,hwBattsGroupName            }
            STATUS current
            DESCRIPTION
                "Battery group discharge alarm. Its correlation binding parameters:  Site ID, Site name, Site description, NE ID, Alarm name, Alarm single description, Alarm port description, Alarm severity, and Site alarm SN. Additionally, in order to identify the device, battery group ID and group name are also include in VB(variable bondings)."
            ::= { hwSiteAlarmTrapsPrefix 13 }

        hwBattDischargeAlarmResumeTraps NOTIFICATION-TYPE
            OBJECTS { hwAlarmTrapOrdinalNumber,hwAlarmText,hwAlarmLevel,hwAlarmSigDesc,hwSiteName,hwSiteAdminAddr,hwNetIdentifier,hwSiteDescription,hwBattsGroupId,hwBattsGroupName            }
            STATUS current
            DESCRIPTION
                "Battery group discharge alarm resume. Its correlation binding parameters:  Site ID, Site name, Site description, NE ID, Alarm name, Alarm single description, Alarm port description, Alarm severity, and Site alarm SN. Additionally, in order to identify the device, battery group ID and group name are also include in VB(variable bondings)."
            ::= { hwSiteAlarmTrapsPrefix 14 }

        hwAcInputAlarmTraps NOTIFICATION-TYPE
            OBJECTS { hwAlarmTrapOrdinalNumber,hwAlarmText,hwAlarmLevel,hwAlarmSigDesc,hwSiteName,hwSiteAdminAddr,hwNetIdentifier,hwSiteDescription,hwAcEquipId,hwAcEquipName,hwAcInputOperStatus            }
            STATUS current
            DESCRIPTION
                "AC absent or AC power off alarms happened. Its correlation binding parameters:  Site ID, Site name, Site description, NE ID, Alarm name, Alarm single description, Alarm port description, Alarm severity, and Site alarm SN. Additionally, in order to identify the device, AC equipment ID and equipment name are also include in VB(variable bondings)."
            ::= { hwSiteAlarmTrapsPrefix 15 }

        hwAcInputAlarmResumeTraps NOTIFICATION-TYPE
            OBJECTS { hwAlarmTrapOrdinalNumber,hwAlarmText,hwAlarmLevel,hwAlarmSigDesc,hwSiteName,hwSiteAdminAddr,hwNetIdentifier,hwSiteDescription,hwAcEquipId,hwAcEquipName,hwAcInputOperStatus            }
            STATUS current
            DESCRIPTION
                "AC input alarm resumed. Its correlation binding parameters:  Site ID, Site name, Site description, NE ID, Alarm name, Alarm single description, Alarm port description, Alarm severity, and Site alarm SN. Additionally, in order to identify the device, AC equipment ID and equipment name are also include in VB(variable bondings)."
            ::= { hwSiteAlarmTrapsPrefix 16 }

        hwDcVoltAlarmTraps NOTIFICATION-TYPE
            OBJECTS { hwAlarmTrapOrdinalNumber,hwAlarmText,hwAlarmLevel,hwAlarmSigDesc,hwSiteName,hwSiteAdminAddr,hwNetIdentifier,hwSiteDescription,hwDcOutputEquipId,hwDcOutputEquipName,hwDcOutputOperStatus            }
            STATUS current
            DESCRIPTION
                "DC voltage alarm. Its correlation binding parameters:  Site ID, Site name, Site description, NE ID, Alarm name, Alarm single description, Alarm port description, Alarm severity, and Site alarm SN. Additionally, in order to identify the device, AC equipment ID and equipment name are also include in VB(variable bondings)."
            ::= { hwSiteAlarmTrapsPrefix 19 }

        hwDcVoltAlarmResumeTraps NOTIFICATION-TYPE
            OBJECTS { hwAlarmTrapOrdinalNumber,hwAlarmText,hwAlarmLevel,hwAlarmSigDesc,hwSiteName,hwSiteAdminAddr,hwNetIdentifier,hwSiteDescription,hwDcOutputEquipId,hwDcOutputEquipName,hwDcOutputOperStatus            }
            STATUS current
            DESCRIPTION
                "DC voltage alarm resume. Its correlation binding parameters:  Site ID, Site name, Site description, NE ID, Alarm name, Alarm single description, Alarm port description, Alarm severity, and Site alarm SN. Additionally, in order to identify the device, DC equipment ID and equipment name are also include in VB(variable bondings)."
            ::= { hwSiteAlarmTrapsPrefix 20 }

        hwLoadLvdAlarmTraps NOTIFICATION-TYPE
            OBJECTS { hwAlarmTrapOrdinalNumber,hwAlarmText,hwAlarmLevel,hwAlarmSigDesc,hwSiteName,hwSiteAdminAddr,hwNetIdentifier,hwSiteDescription,hwLvdUnitEquipId,hwLvdUnitEquipName,hwLvdBranchOperStatus            }
            STATUS current
            DESCRIPTION
                "Loads disconnect for low voltage. Its correlation binding parameters:  Site ID, Site name, Site description, NE ID, Alarm name, Alarm single description, Alarm port description, Alarm severity, and Site alarm SN. Additionally, in order to identify the device, load LVD unit equipment ID and equipment name are also include in VB(variable bondings)."
            ::= { hwSiteAlarmTrapsPrefix 21 }

        hwLoadLvdAlarmResumeTraps NOTIFICATION-TYPE
            OBJECTS { hwAlarmTrapOrdinalNumber,hwAlarmText,hwAlarmLevel,hwAlarmSigDesc,hwSiteName,hwSiteAdminAddr,hwNetIdentifier,hwSiteDescription,hwLvdUnitEquipId,hwLvdUnitEquipName,hwLvdBranchOperStatus            }
            STATUS current
            DESCRIPTION
                "Load LVD alarm resume. Its correlation binding parameters:  Site ID, Site name, Site description, NE ID, Alarm name, Alarm single description, Alarm port description, Alarm severity, and Site alarm SN. Additionally, in order to identify the device, load LVD unit equipment ID and equipment name are also include in VB(variable bondings)."
            ::= { hwSiteAlarmTrapsPrefix 22 }

        hwLoadFuseAlarmTraps NOTIFICATION-TYPE
            OBJECTS { hwAlarmTrapOrdinalNumber,hwAlarmText,hwAlarmLevel,hwAlarmSigDesc,hwSiteName,hwSiteAdminAddr,hwNetIdentifier,hwSiteDescription,hwDcOutputEquipId,hwDcOutputEquipName            }
            STATUS current
            DESCRIPTION
                "Load fuse broken down. Its correlation binding parameters:  Site ID, Site name, Site description, NE ID, Alarm name, Alarm single description, Alarm port description, Alarm severity, and Site alarm SN. Additionally, in order to identify the device, battery string equipment ID and equipment name are also include in VB(variable bondings)."
            ::= { hwSiteAlarmTrapsPrefix 23 }

        hwLoadFuseAlarmResumeTraps NOTIFICATION-TYPE
            OBJECTS { hwAlarmTrapOrdinalNumber,hwAlarmText,hwAlarmLevel,hwAlarmSigDesc,hwSiteName,hwSiteAdminAddr,hwNetIdentifier,hwSiteDescription,hwDcOutputEquipId,hwDcOutputEquipName            }
            STATUS current
            DESCRIPTION
                "Load fuse alarm resume. Its correlation binding parameters:  Site ID, Site name, Site description, NE ID, Alarm name, Alarm single description, Alarm port description, Alarm severity, and Site alarm SN. Additionally, in order to identify the device, battery string equipment ID and equipment name are also include in VB(variable bondings)."
            ::= { hwSiteAlarmTrapsPrefix 24 }

        hwEnvTempAlarmTraps NOTIFICATION-TYPE
            OBJECTS { hwAlarmTrapOrdinalNumber,hwAlarmText,hwAlarmLevel,hwAlarmSigDesc,hwSiteName,hwSiteAdminAddr,hwNetIdentifier,hwSiteDescription,hwEnvTempEquipId,hwEnvTempEquipName,hwEnvTempSensorOperStatus            }
            STATUS current
            DESCRIPTION
                "Environment temperature is too high or too low. Its correlation binding parameters:  Site ID, Site name, Site description, NE ID, Alarm name, Alarm single description, Alarm port description, Alarm severity, and Site alarm SN. Additionally, in order to identify the device, envirenment temperature sensor equipment ID and equipment name are also include in VB(variable bondings)."
            ::= { hwSiteAlarmTrapsPrefix 25 }

        hwEnvTempAlarmResumeTraps NOTIFICATION-TYPE
            OBJECTS { hwAlarmTrapOrdinalNumber,hwAlarmText,hwAlarmLevel,hwAlarmSigDesc,hwSiteName,hwSiteAdminAddr,hwNetIdentifier,hwSiteDescription,hwEnvTempEquipId,hwEnvTempEquipName,hwEnvTempSensorOperStatus            }
            STATUS current
            DESCRIPTION
                "Environment temperature alarm resume. Its correlation binding parameters:  Site ID, Site name, Site description, NE ID, Alarm name, Alarm single description, Alarm port description, Alarm severity, and Site alarm SN. Additionally, in order to identify the device, envirenment temperature sensor equipment ID and equipment name are also include in VB(variable bondings)."
            ::= { hwSiteAlarmTrapsPrefix 26 }

        hwSpareDigitalAlarmTraps NOTIFICATION-TYPE
            OBJECTS { hwAlarmTrapOrdinalNumber,hwAlarmText,hwAlarmLevel,hwAlarmSigDesc,hwSiteName,hwSiteAdminAddr,hwNetIdentifier,hwSiteDescription,hwSpareDigitalEquipId,hwSpareDigitalEquipName,hwSpareDigitalOperStatus            }
            STATUS current
            DESCRIPTION
                "Spare digital fault. Its correlation binding parameters:  Site ID, Site name, Site description, NE ID, Alarm name, Alarm single description, Alarm port description, Alarm severity, and Site alarm SN. Additionally, in order to identify the device, Spare digital equipment ID and equipment name are also include in VB(variable bondings)."
            ::= { hwSiteAlarmTrapsPrefix 29 }

        hwSpareDigitalAlarmResumeTraps NOTIFICATION-TYPE
            OBJECTS { hwAlarmTrapOrdinalNumber,hwAlarmText,hwAlarmLevel,hwAlarmSigDesc,hwSiteName,hwSiteAdminAddr,hwNetIdentifier,hwSiteDescription,hwSpareDigitalEquipId,hwSpareDigitalEquipName,hwSpareDigitalOperStatus            }
            STATUS current
            DESCRIPTION
                "Spare digital alarm resume.Its correlation binding parameters:  Site ID, Site name, Site description, NE ID, Alarm name, Alarm single description, Alarm port description, Alarm severity, and Site alarm SN. Additionally, in order to identify the device, Spare digital equipment ID and equipment name are also include in VB(variable bondings)."
            ::= { hwSiteAlarmTrapsPrefix 30 }

        hwDoorAlarmTraps NOTIFICATION-TYPE
            OBJECTS { hwAlarmTrapOrdinalNumber,hwAlarmText,hwAlarmLevel,hwAlarmSigDesc,hwSiteName,hwSiteAdminAddr,hwNetIdentifier,hwSiteDescription,hwEnvUnitsGroupId,hwEnvUnitsGroupName            }
            STATUS current
            DESCRIPTION
                "Door open. Its correlation binding parameters:  Site ID, Site name, Site description, NE ID, Alarm name, Alarm single description, Alarm port description, Alarm severity, and Site alarm SN. Additionally, in order to identify the device, envirenment unit group ID and group name are also include in VB(variable bondings)."
            ::= { hwSiteAlarmTrapsPrefix 31 }

        hwDoorAlarmResumeTraps NOTIFICATION-TYPE
            OBJECTS { hwAlarmTrapOrdinalNumber,hwAlarmText,hwAlarmLevel,hwAlarmSigDesc,hwSiteName,hwSiteAdminAddr,hwNetIdentifier,hwSiteDescription,hwEnvUnitsGroupId,hwEnvUnitsGroupName            }
            STATUS current
            DESCRIPTION
                "Door alarm resume. Its correlation binding parameters:  Site ID, Site name, Site description, NE ID, Alarm name, Alarm single description, Alarm port description, Alarm severity, and Site alarm SN. Additionally, in order to identify the device, envirenment unit group ID and group name are also include in VB(variable bondings)."
            ::= { hwSiteAlarmTrapsPrefix 32 }

        hwWaterAlarmTraps NOTIFICATION-TYPE
            OBJECTS { hwAlarmTrapOrdinalNumber,hwAlarmText,hwAlarmLevel,hwAlarmSigDesc,hwSiteName,hwSiteAdminAddr,hwNetIdentifier,hwSiteDescription,hwEnvUnitsGroupId,hwEnvUnitsGroupName            }
            STATUS current
            DESCRIPTION
                "Water alarm. Its correlation binding parameters:  Site ID, Site name, Site description, NE ID, Alarm name, Alarm single description, Alarm port description, Alarm severity, and Site alarm SN. Additionally, in order to identify the device, envirenment unit group ID and group name are also include in VB(variable bondings)."
            ::= { hwSiteAlarmTrapsPrefix 33 }

        hwWaterAlarmResumeTraps NOTIFICATION-TYPE
            OBJECTS { hwAlarmTrapOrdinalNumber,hwAlarmText,hwAlarmLevel,hwAlarmSigDesc,hwSiteName,hwSiteAdminAddr,hwNetIdentifier,hwSiteDescription,hwEnvUnitsGroupId,hwEnvUnitsGroupName            }
            STATUS current
            DESCRIPTION
                "Water alarm resume. Its correlation binding parameters:  Site ID, Site name, Site description, NE ID, Alarm name, Alarm single description, Alarm port description, Alarm severity, and Site alarm SN. Additionally, in order to identify the device, envirenment unit group ID and group name are also include in VB(variable bondings)."
            ::= { hwSiteAlarmTrapsPrefix 34 }

        hwSmokeAlarmTraps NOTIFICATION-TYPE
            OBJECTS { hwAlarmTrapOrdinalNumber,hwAlarmText,hwAlarmLevel,hwAlarmSigDesc,hwSiteName,hwSiteAdminAddr,hwNetIdentifier,hwSiteDescription,hwEnvUnitsGroupId,hwEnvUnitsGroupName            }
            STATUS current
            DESCRIPTION
                "Site is on fire, which is detected by smoke sensors. Its correlation binding parameters:  Site ID, Site name, Site description, NE ID, Alarm name, Alarm single description, Alarm port description, Alarm severity, and Site alarm SN. Additionally, in order to identify the device, envirenment unit group ID and group name are also include in VB(variable bondings)."
            ::= { hwSiteAlarmTrapsPrefix 35 }

        hwSmokeAlarmResumeTraps NOTIFICATION-TYPE
            OBJECTS { hwAlarmTrapOrdinalNumber,hwAlarmText,hwAlarmLevel,hwAlarmSigDesc,hwSiteName,hwSiteAdminAddr,hwNetIdentifier,hwSiteDescription,hwEnvUnitsGroupId,hwEnvUnitsGroupName            }
            STATUS current
            DESCRIPTION
                "Smoke alarm resume. Its correlation binding parameters:  Site ID, Site name, Site description, NE ID, Alarm name, Alarm single description, Alarm port description, Alarm severity, and Site alarm SN. Additionally, in order to identify the device, envirenment unit group ID and group name are also include in VB(variable bondings)."
            ::= { hwSiteAlarmTrapsPrefix 36 }

        hwMultiRectFailureAlarmTraps NOTIFICATION-TYPE
            OBJECTS { hwAlarmTrapOrdinalNumber,hwAlarmText,hwAlarmLevel,hwAlarmSigDesc,hwSiteName,hwSiteAdminAddr,hwNetIdentifier,hwSiteDescription,hwRectsGroupId,hwRectsGroupName            }
            STATUS current
            DESCRIPTION
                "More than one rectifier reported fault alarms in the same time. Its correlation binding parameters:  Site ID, Site name, Site description, NE ID, Alarm name, Alarm single description, Alarm port description, Alarm severity, and Site alarm SN. Additionally, in order to identify the device, rectifier group ID and group name are also include in VB(variable bondings)."
            ::= { hwSiteAlarmTrapsPrefix 41 }

        hwMultiRectFailureAlarmResumeTraps NOTIFICATION-TYPE
            OBJECTS { hwAlarmTrapOrdinalNumber,hwAlarmText,hwAlarmLevel,hwAlarmSigDesc,hwSiteName,hwSiteAdminAddr,hwNetIdentifier,hwSiteDescription,hwRectsGroupId,hwRectsGroupName            }
            STATUS current
            DESCRIPTION
                "Multi-rectifiers fault alarm resume. Its correlation binding parameters:  Site ID, Site name, Site description, NE ID, Alarm name, Alarm single description, Alarm port description, Alarm severity, and Site alarm SN. Additionally, in order to identify the device, rectifier group ID and group name are also include in VB(variable bondings)."
            ::= { hwSiteAlarmTrapsPrefix 42 }

        hwRectRedundAlarmTraps NOTIFICATION-TYPE
            OBJECTS { hwAlarmTrapOrdinalNumber,hwAlarmText,hwAlarmLevel,hwAlarmSigDesc,hwSiteName,hwSiteAdminAddr,hwNetIdentifier,hwSiteDescription,hwRectsGroupId,hwRectsGroupName            }
            STATUS current
            DESCRIPTION
                "Rectifiers work redundantly, in this case that some of rectifiers will going to sleep. Its correlation binding parameters:  Site ID, Site name, Site description, NE ID, Alarm name, Alarm single description, Alarm port description, Alarm severity, and Site alarm SN. Additionally, in order to identify the device, rectifier group ID and group name are also include in VB(variable bondings)."
            ::= { hwSiteAlarmTrapsPrefix 43 }

        hwRectRedundAlarmResumeTraps NOTIFICATION-TYPE
            OBJECTS { hwAlarmTrapOrdinalNumber,hwAlarmText,hwAlarmLevel,hwAlarmSigDesc,hwSiteName,hwSiteAdminAddr,hwNetIdentifier,hwSiteDescription,hwRectsGroupId,hwRectsGroupName            }
            STATUS current
            DESCRIPTION
                "Rectifiers redundant alarm resume, when the power supply and requirement were in balance. Its correlation binding parameters:  Site ID, Site name, Site description, NE ID, Alarm name, Alarm single description, Alarm port description, Alarm severity, and Site alarm SN. Additionally, in order to identify the device, rectifier group ID and group name are also include in VB(variable bondings)."
            ::= { hwSiteAlarmTrapsPrefix 44 }

        hwBattUnbalanceAlarmTraps NOTIFICATION-TYPE
            OBJECTS { hwAlarmTrapOrdinalNumber,hwAlarmText,hwAlarmLevel,hwAlarmSigDesc,hwSiteName,hwSiteAdminAddr,hwNetIdentifier,hwSiteDescription,hwBattStringEquipId,hwBattStringEquipName,hwBattStringOperStatus            }
            STATUS current
            DESCRIPTION
                "Battery works in unbalance state. Its correlation binding parameters:  Site ID, Site name, Site description, NE ID, Alarm name, Alarm single description, Alarm port description, Alarm severity, and Site alarm SN. Additionally, in order to identify the device, battery string equipment ID and equipment name are also include in VB(variable bondings)."
            ::= { hwSiteAlarmTrapsPrefix 45 }

        hwBattUnbalanceAlarmResumeTraps NOTIFICATION-TYPE
            OBJECTS { hwAlarmTrapOrdinalNumber,hwAlarmText,hwAlarmLevel,hwAlarmSigDesc,hwSiteName,hwSiteAdminAddr,hwNetIdentifier,hwSiteDescription,hwBattStringEquipId,hwBattStringEquipName,hwBattStringOperStatus            }
            STATUS current
            DESCRIPTION
                "Battery unbalance alarm resume. Its correlation binding parameters:  Site ID, Site name, Site description, NE ID, Alarm name, Alarm single description, Alarm port description, Alarm severity, and Site alarm SN. Additionally, in order to identify the device, battery string equipment ID and equipment name are also include in VB(variable bondings)."
            ::= { hwSiteAlarmTrapsPrefix 46 }

        hwSpdAlarmTraps NOTIFICATION-TYPE
            OBJECTS { hwAlarmTrapOrdinalNumber,hwAlarmText,hwAlarmLevel,hwAlarmSigDesc,hwSiteName,hwSiteAdminAddr,hwNetIdentifier,hwSiteDescription,hwEnvUnitsGroupId,hwEnvUnitsGroupName            }
            STATUS current
            DESCRIPTION
                "Description."
            ::= { hwSiteAlarmTrapsPrefix 57 }

        hwSpdAlarmResumeTraps NOTIFICATION-TYPE
            OBJECTS { hwAlarmTrapOrdinalNumber,hwAlarmText,hwAlarmLevel,hwAlarmSigDesc,hwSiteName,hwSiteAdminAddr,hwNetIdentifier,hwSiteDescription,hwEnvUnitsGroupId,hwEnvUnitsGroupName            }
            STATUS current
            DESCRIPTION
                "Description."
            ::= { hwSiteAlarmTrapsPrefix 58 }

        hwMissingBattTempSensorTraps NOTIFICATION-TYPE
            OBJECTS { hwAlarmTrapOrdinalNumber,hwAlarmText,hwAlarmLevel,hwAlarmSigDesc,hwSiteName,hwSiteAdminAddr,hwNetIdentifier,hwSiteDescription,hwBattsGroupId,hwBattsGroupName            }
            STATUS current
            DESCRIPTION
                "Description."
            ::= { hwSiteAlarmTrapsPrefix 75 }

        hwMissingBattTempSensorResumeTraps NOTIFICATION-TYPE
            OBJECTS { hwAlarmTrapOrdinalNumber,hwAlarmText,hwAlarmLevel,hwAlarmSigDesc,hwSiteName,hwSiteAdminAddr,hwNetIdentifier,hwSiteDescription,hwBattsGroupId,hwBattsGroupName            }
            STATUS current
            DESCRIPTION
                "Description."
            ::= { hwSiteAlarmTrapsPrefix 76 }

        hwBattTempSensorFaultTraps NOTIFICATION-TYPE
            OBJECTS { hwAlarmTrapOrdinalNumber,hwAlarmText,hwAlarmLevel,hwAlarmSigDesc,hwSiteName,hwSiteAdminAddr,hwNetIdentifier,hwSiteDescription,hwBattsGroupId,hwBattsGroupName            }
            STATUS current
            DESCRIPTION
                "Description."
            ::= { hwSiteAlarmTrapsPrefix 77 }

        hwBattTempSensorFaultResumeTraps NOTIFICATION-TYPE
            OBJECTS { hwAlarmTrapOrdinalNumber,hwAlarmText,hwAlarmLevel,hwAlarmSigDesc,hwSiteName,hwSiteAdminAddr,hwNetIdentifier,hwSiteDescription,hwBattsGroupId,hwBattsGroupName            }
            STATUS current
            DESCRIPTION
                "Description."
            ::= { hwSiteAlarmTrapsPrefix 78 }

        hwAcOverVoltageTraps NOTIFICATION-TYPE
            OBJECTS { hwAlarmTrapOrdinalNumber,hwAlarmText,hwAlarmLevel,hwAlarmSigDesc,hwSiteName,hwSiteAdminAddr,hwNetIdentifier,hwSiteDescription,hwAcEquipId,hwAcEquipName,hwAcInputOperStatus            }
            STATUS current
            DESCRIPTION
                "Description."
            ::= { hwSiteAlarmTrapsPrefix 79 }

        hwAcOverVoltageResumeTraps NOTIFICATION-TYPE
            OBJECTS { hwAlarmTrapOrdinalNumber,hwAlarmText,hwAlarmLevel,hwAlarmSigDesc,hwSiteName,hwSiteAdminAddr,hwNetIdentifier,hwSiteDescription,hwAcEquipId,hwAcEquipName,hwAcInputOperStatus            }
            STATUS current
            DESCRIPTION
                "Description."
            ::= { hwSiteAlarmTrapsPrefix 80 }

        hwAcUnderVoltageTraps NOTIFICATION-TYPE
            OBJECTS { hwAlarmTrapOrdinalNumber,hwAlarmText,hwAlarmLevel,hwAlarmSigDesc,hwSiteName,hwSiteAdminAddr,hwNetIdentifier,hwSiteDescription,hwAcEquipId,hwAcEquipName,hwAcInputOperStatus            }
            STATUS current
            DESCRIPTION
                "Description."
            ::= { hwSiteAlarmTrapsPrefix 81 }

        hwAcUnderVoltageResumeTraps NOTIFICATION-TYPE
            OBJECTS { hwAlarmTrapOrdinalNumber,hwAlarmText,hwAlarmLevel,hwAlarmSigDesc,hwSiteName,hwSiteAdminAddr,hwNetIdentifier,hwSiteDescription,hwAcEquipId,hwAcEquipName,hwAcInputOperStatus            }
            STATUS current
            DESCRIPTION
                "Description."
            ::= { hwSiteAlarmTrapsPrefix 82 }

        hwTcuDcAirAlarmTraps NOTIFICATION-TYPE
            OBJECTS { hwAlarmTrapOrdinalNumber,hwAlarmText,hwAlarmLevel,hwAlarmSigDesc,hwSiteName,hwSiteAdminAddr,hwNetIdentifier,hwSiteDescription,hwDcAirEquipId,hwDcAirEquipName,hwDcAirOperStatus            }
            STATUS current
            DESCRIPTION
                "Description."
            ::= { hwSiteAlarmTrapsPrefix 85 }

        hwTcuDcAirAlarmResumeTraps NOTIFICATION-TYPE
            OBJECTS { hwAlarmTrapOrdinalNumber,hwAlarmText,hwAlarmLevel,hwAlarmSigDesc,hwSiteName,hwSiteAdminAddr,hwNetIdentifier,hwSiteDescription,hwDcAirEquipId,hwDcAirEquipName,hwDcAirOperStatus            }
            STATUS current
            DESCRIPTION
                "Description."
            ::= { hwSiteAlarmTrapsPrefix 86 }

        hwSSUSummaryAlarmTraps NOTIFICATION-TYPE
            OBJECTS { hwAlarmTrapOrdinalNumber,hwAlarmText,hwAlarmLevel,hwAlarmSigDesc,hwSiteName,hwSiteAdminAddr,hwNetIdentifier,hwSiteDescription,hwSSUGroupId,hwSSUGroupName            }
            STATUS current
            DESCRIPTION
                "Description."
            ::= { hwSiteAlarmTrapsPrefix 123 }

        hwSSUSummaryAlarmResumeTraps NOTIFICATION-TYPE
            OBJECTS { hwAlarmTrapOrdinalNumber,hwAlarmText,hwAlarmLevel,hwAlarmSigDesc,hwSiteName,hwSiteAdminAddr,hwNetIdentifier,hwSiteDescription,hwSSUGroupId,hwSSUGroupName            }
            STATUS current
            DESCRIPTION
                "Description."
            ::= { hwSiteAlarmTrapsPrefix 124 }

        hwSSUAlarmTraps NOTIFICATION-TYPE
            OBJECTS { hwAlarmTrapOrdinalNumber,hwAlarmText,hwAlarmLevel,hwAlarmSigDesc,hwSiteName,hwSiteAdminAddr,hwNetIdentifier,hwSiteDescription,hwSSUEquipId,hwSSUEquipName            }
            STATUS current
            DESCRIPTION
                "Description."
            ::= { hwSiteAlarmTrapsPrefix 125 }

        hwSSUAlarmResumeTraps NOTIFICATION-TYPE
            OBJECTS { hwAlarmTrapOrdinalNumber,hwAlarmText,hwAlarmLevel,hwAlarmSigDesc,hwSiteName,hwSiteAdminAddr,hwNetIdentifier,hwSiteDescription,hwSSUEquipId,hwSSUEquipName            }
            STATUS current
            DESCRIPTION
                "Description."
            ::= { hwSiteAlarmTrapsPrefix 126 }

        hwBatteryLostAlarmTraps NOTIFICATION-TYPE
            OBJECTS { hwAlarmTrapOrdinalNumber,hwAlarmText,hwAlarmLevel,hwAlarmSigDesc,hwSiteName,hwSiteAdminAddr,hwNetIdentifier,hwSiteDescription,hwBattStringEquipId,hwBattStringEquipName            }
            STATUS current
            DESCRIPTION
                "Some battery strings could be lost, when the alarm happened."
            ::= { hwSiteAlarmTrapsPrefix 171 }

        hwBatteryLostAlarmResumeTraps NOTIFICATION-TYPE
            OBJECTS { hwAlarmTrapOrdinalNumber,hwAlarmText,hwAlarmLevel,hwAlarmSigDesc,hwSiteName,hwSiteAdminAddr,hwNetIdentifier,hwSiteDescription,hwBattStringEquipId,hwBattStringEquipName            }
            STATUS current
            DESCRIPTION
                "If all the battery strings can be detected, the alarm of battery losting resume."
            ::= { hwSiteAlarmTrapsPrefix 172 }

        hwRectCapacityAlarmTraps NOTIFICATION-TYPE
            OBJECTS { hwAlarmTrapOrdinalNumber,hwAlarmText,hwAlarmLevel,hwAlarmSigDesc,hwSiteName,hwSiteAdminAddr,hwNetIdentifier,hwSiteDescription,hwRectsGroupId,hwRectsGroupName            }
            STATUS current
            DESCRIPTION
                "Low Rectifier Capacity or High Rectifier Capacity Alarm happened."
            ::= { hwSiteAlarmTrapsPrefix 131 }

        hwRectCapacityAlarmResumeTraps NOTIFICATION-TYPE
            OBJECTS { hwAlarmTrapOrdinalNumber,hwAlarmText,hwAlarmLevel,hwAlarmSigDesc,hwSiteName,hwSiteAdminAddr,hwNetIdentifier,hwSiteDescription,hwRectsGroupId,hwRectsGroupName            }
            STATUS current
            DESCRIPTION
                "Low Rectifier Capacity or High Rectifier Capacity Alarm Resumed."
            ::= { hwSiteAlarmTrapsPrefix 132 }

        hwAcbGroupAlmTrapTable OBJECT IDENTIFIER ::= { hwSiteAlarmTraps 2 }

        hwAcbGroupAlmTrapTablePrefix OBJECT IDENTIFIER ::= { hwAcbGroupAlmTrapTable 0 }

        hwAcbGroupAlarmTrap NOTIFICATION-TYPE
            OBJECTS { hwAlarmTrapOrdinalNumber,hwAlarmText,hwAlarmLevel,hwAlarmSigDesc,hwSiteName,hwSiteAdminAddr,hwNetIdentifier,hwSiteDescription,hwAcbGroupEquipId,hwAcbGroupEquipName            }
            STATUS current
            DESCRIPTION
                "/"
            ::= { hwAcbGroupAlmTrapTablePrefix 99 }

        hwAcbGroupAarlmResumeTrap NOTIFICATION-TYPE
            OBJECTS { hwAlarmTrapOrdinalNumber,hwAlarmText,hwAlarmLevel,hwAlarmSigDesc,hwSiteName,hwSiteAdminAddr,hwNetIdentifier,hwSiteDescription,hwAcbGroupEquipId,hwAcbGroupEquipName            }
            STATUS current
            DESCRIPTION
                "/"
            ::= { hwAcbGroupAlmTrapTablePrefix 100 }

        hwAcbAlmTrapTable OBJECT IDENTIFIER ::= { hwSiteAlarmTraps 3 }

        hwAcbAlmTrapTablePrefix OBJECT IDENTIFIER ::= { hwAcbAlmTrapTable 0 }

        hwAcbAlarmTrap NOTIFICATION-TYPE
            OBJECTS { hwAlarmTrapOrdinalNumber,hwAlarmText,hwAlarmLevel,hwAlarmSigDesc,hwSiteName,hwSiteAdminAddr,hwNetIdentifier,hwSiteDescription,hwAcbEquipId,hwAcbEquipName            }
            STATUS current
            DESCRIPTION
                "/"
            ::= { hwAcbAlmTrapTablePrefix 99 }

        hwAcbAarlmResumeTrap NOTIFICATION-TYPE
            OBJECTS { hwAlarmTrapOrdinalNumber,hwAlarmText,hwAlarmLevel,hwAlarmSigDesc,hwSiteName,hwSiteAdminAddr,hwNetIdentifier,hwSiteDescription,hwAcbEquipId,hwAcbEquipName            }
            STATUS current
            DESCRIPTION
                "/"
            ::= { hwAcbAlmTrapTablePrefix 100 }

        hwAcAmmeterAlmTrapTable OBJECT IDENTIFIER ::= { hwSiteAlarmTraps 8 }

        hwAcAmmeterAlmTrapPrefix OBJECT IDENTIFIER ::= { hwAcAmmeterAlmTrapTable 0 }

        hwAcAmmeterAlarmTrap NOTIFICATION-TYPE
            OBJECTS { hwAlarmTrapOrdinalNumber,hwAlarmText,hwAlarmLevel,hwAlarmSigDesc,hwSiteName,hwSiteAdminAddr,hwNetIdentifier,hwSiteDescription,hwAcAmmeterEquipId,hwAcAmmeterEquipName            }
            STATUS current
            DESCRIPTION
                "Ac Ammeter.
                Its correlation binding parameters: 
                Site alarm serial number (SN),
                Alarm name,
                Alarm level,
                Site name,
                Site administrant address,
                NE ID,
                Site description,
                Additionally, in order to identify the device, rectifier equipment ID and equipment name are also include in VB(variable bondings)."
            ::= { hwAcAmmeterAlmTrapPrefix 1 }

        hwAcAmmeterAlarmResumeTrap NOTIFICATION-TYPE
            OBJECTS { hwAlarmTrapOrdinalNumber,hwAlarmText,hwAlarmLevel,hwAlarmSigDesc,hwSiteName,hwSiteAdminAddr,hwNetIdentifier,hwSiteDescription,hwAcAmmeterEquipId,hwAcAmmeterEquipName            }
            STATUS current
            DESCRIPTION
                "Ac Ammeter .
                Its correlation binding parameters: 
                Site alarm serial number (SN),
                Alarm name,
                Alarm level,
                Site name,
                Site administrant address,
                NE ID,
                Site description,
                Additionally, in order to identify the device, rectifier equipment ID and equipment name are also include in VB(variable bondings)."
            ::= { hwAcAmmeterAlmTrapPrefix 2 }

        hwElockAlmTrapTable OBJECT IDENTIFIER ::= { hwSiteAlarmTraps 13 }

        hwElockAlmTrapTablePrefix OBJECT IDENTIFIER ::= { hwElockAlmTrapTable 0 }

        hwElockAlarmTrap NOTIFICATION-TYPE
            OBJECTS { hwAlarmTrapOrdinalNumber,hwAlarmText,hwAlarmLevel,hwAlarmSigDesc,hwSiteName,hwSiteAdminAddr,hwNetIdentifier,hwSiteDescription,hwElockEquipId,hwElockEquipName            }
            STATUS current
            DESCRIPTION
                "/"
            ::= { hwElockAlmTrapTablePrefix 1 }

        hwElockAlarmResumeTrap NOTIFICATION-TYPE
            OBJECTS { hwAlarmTrapOrdinalNumber,hwAlarmText,hwAlarmLevel,hwAlarmSigDesc,hwSiteName,hwSiteAdminAddr,hwNetIdentifier,hwSiteDescription,hwElockEquipId,hwElockEquipName            }
            STATUS current
            DESCRIPTION
                "/"
            ::= { hwElockAlmTrapTablePrefix 2 }

        hwTemHumAlmTrapTable OBJECT IDENTIFIER ::= { hwSiteAlarmTraps 14 }

        hwTemHumAlmTrapTablePrefix OBJECT IDENTIFIER ::= { hwTemHumAlmTrapTable 0 }

        hwTemHumAlarmTrap NOTIFICATION-TYPE
            OBJECTS { hwAlarmTrapOrdinalNumber,hwAlarmText,hwAlarmLevel,hwAlarmSigDesc,hwSiteName,hwSiteAdminAddr,hwNetIdentifier,hwSiteDescription,hwTemHumEquipId,hwTemHumEquipName            }
            STATUS current
            DESCRIPTION
                "/"
            ::= { hwTemHumAlmTrapTablePrefix 1 }

        hwTemHumAlarmResumeTrap NOTIFICATION-TYPE
            OBJECTS { hwAlarmTrapOrdinalNumber,hwAlarmText,hwAlarmLevel,hwAlarmSigDesc,hwSiteName,hwSiteAdminAddr,hwNetIdentifier,hwSiteDescription,hwTemHumEquipId,hwTemHumEquipName            }
            STATUS current
            DESCRIPTION
                "/"
            ::= { hwTemHumAlmTrapTablePrefix 2 }

        hwSiteDevicesTraps OBJECT IDENTIFIER ::= { hwSiteMonitorMIBTraps 2 }

        hwDevicesTrapsPrefix OBJECT IDENTIFIER ::= { hwSiteDevicesTraps 0 }

        hwRectifiersInslotChange NOTIFICATION-TYPE
            OBJECTS { hwDeviceTrapOrdinalNumber,hwSiteName,hwSiteAdminAddr,hwNetIdentifier,hwSiteDescription,hwRectEquipId,hwRectEquipName,hwRectOperStatus            }
            STATUS current
            DESCRIPTION
                "When the presence status of a rectifier changes, the node reports an event. Then the NMS adds or deletes the corresponding entry to or from hwRectConfigTable or hwRectOperTable. The bound information includes the site address, site name, site description, and NE identifier. In addition, the ID, name, and status of the rectifier are bound to identify the specific rectifier and its operation type. When an entry is added, the device status is reported as normal (1); when an entry is deleted, the device status is reported as commFail (4).
                  This trap is the unique trigger condition that causes the NMS to add or delete entries to or from hwRectConfigTable or hwRectOperTable.
                "
            ::= { hwDevicesTrapsPrefix 1 }

        hwBatterysInslotChange NOTIFICATION-TYPE
            OBJECTS { hwDeviceTrapOrdinalNumber,hwSiteName,hwSiteAdminAddr,hwNetIdentifier,hwSiteDescription,hwBattStringEquipId,hwBattStringEquipName,hwBattStringOperStatus            }
            STATUS current
            DESCRIPTION
                "When the presence status of a battery string changes, the node reports an event. Then the NMS adds or deletes the corresponding entry to or from hwBatttConfigTable or hwBatttOperTable. The bound information includes the site address, site name, site description, and NE identifier. 
                In addition, the ID, name, and status of the battery string are bound to identify the specific battery string and its operation type. 
                When an entry is added, the device status is reported as normal (1); 
                when an entry is deleted, the device status is reported as loopBreak (4).
                  This trap is the unique trigger condition that causes the NMS to add or delete entries to or from hwBatttConfigTable or hwBatttOperTable."
            ::= { hwDevicesTrapsPrefix 2 }

        hwBattTestRecordsAdd NOTIFICATION-TYPE
            OBJECTS { hwDeviceTrapOrdinalNumber,hwSiteName,hwSiteAdminAddr,hwNetIdentifier,hwSiteDescription            }
            STATUS current
            DESCRIPTION
                "After a new discharge test is conducted on a battery group, the node reports an event. The bound information includes the site address, site name, site description, and NE identifier. The NMS needs to add the corresponding entry to the battery test table. The test records are sorted by time in descending order. The battery test table holds a maximum of 10 test records. If the number of test records exceeds 10, the earlier records starting from the last but one record are deleted at a time because the last record is saved permanently.
                  This trap is the unique trigger condition that causes the NMS to add entries from hwBattsTestResultTable.
                  The battery test table allows you only to add entries."
            ::= { hwDevicesTrapsPrefix 3 }

        hwEnvTempSensInslotChange NOTIFICATION-TYPE
            OBJECTS { hwDeviceTrapOrdinalNumber,hwSiteName,hwSiteAdminAddr,hwNetIdentifier,hwSiteDescription,hwEnvTempEquipId,hwEnvTempEquipName,hwEnvTempSensorOperStatus            }
            STATUS current
            DESCRIPTION
                "When the presence status of an environment temperature sensor changes, the node reports an event. Then the NMS adds or deletes the corresponding entry to or from hwEvnTempSensorTable. The bound information includes the site address, site name, site description, and NE identifier. In addition, the ID, name, and status of the environment temperature sensor are bound to identify the specific environment temperature sensor and its operation type. When an entry is added, the device status is reported as normal (1); when an entry is deleted, the device status is reported as notInslot (4).
                  This trap is the unique trigger condition that causes the NMS to add or delete entries to or from hwEnvTempSensorTable."
            ::= { hwDevicesTrapsPrefix 4 }

        hwEnvHumiSensInslotChange NOTIFICATION-TYPE
            OBJECTS { hwDeviceTrapOrdinalNumber,hwSiteName,hwSiteAdminAddr,hwNetIdentifier,hwSiteDescription,hwEnvHumiEquipId,hwEnvHumiEquipName,hwEnvHumiSensorOperStatus            }
            STATUS current
            DESCRIPTION
                "When the presence status of an environment humidity sensor changes, the trap reports an event. Then the NMS adds or deletes the corresponding entry to or from hwEvnHumiSensorTable. The bound information includes the site address, site name, site description, and NE identifier. In addition, the ID, name, and status of the environment humidity sensor are bound to identify the specific environment humidity sensor and its operation type. When an entry is added, the device status is reported as normal (1); when an entry is deleted, the device status is reported as notInslot (4).
                  This trap is the unique trigger condition that causes the NMS to add or delete entries to or from hwEnvHumiSensorTable."
            ::= { hwDevicesTrapsPrefix 5 }

END
